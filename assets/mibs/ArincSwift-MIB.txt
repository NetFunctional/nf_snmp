---------------------------------------------------------------------------------------
--                                                                                   --
--                               ArincSwift-MIB Definion                             --
--                                     Version 1.0                                   --
--                                                                                   --
---------------------------------------------------------------------------------------
--                                                                                   --
--  This MIB defines a status interface of an aironautic                             --
--  - standalone swift64,                                                            --
--  - standalone swiftBroadband or                                                   --
--  - combined swift 64 and swift braodband                                          --
--  sattelite modem terminal to be used in all type of aircrafts.                    --
--                                                                                   --
---------------------------------------------------------------------------------------
--                                                                                   --
-- Generated by                                                                      --
--   Dipl. Ing. (FH) Manfred Benten                                                  --
--   Honico Technology GmbH                                                          --
--   Hopfensack 19                                                                   --
--   20457 Hamburg                                                                   --
--                                                                                   --
-- on behalf of                                                                      --
--   AIRBUS DEUTSCHLAND GmbH                                                         --
--   BCEYA1 - Cabin Network System Definitions                                       --
--   Kreetslag 10                                                                    --
--   D-21129 Hamburg                                                                 --
--   Phone: +49 40 743 89809                                                         --
--   Mail:  Manfred.Benten@airbus.com                                                --
--                                                                                   --
---------------------------------------------------------------------------------------
ArincSwift-MIB DEFINITIONS ::= BEGIN
IMPORTS
   pppLinkStatusPhysicalIndex
      FROM PPP-LCP-MIB
   ifIndex
      FROM RFC1213-MIB
   OBJECT-GROUP, NOTIFICATION-GROUP
      FROM SNMPv2-CONF
   IpAddress, Integer32, OBJECT-TYPE, MODULE-IDENTITY, NOTIFICATION-TYPE
      FROM SNMPv2-SMI
   TEXTUAL-CONVENTION, TruthValue, DisplayString
      FROM SNMPv2-TC
   enterprises, TimeTicks
      FROM RFC-1155-SMI;

aeec                                      -- 1.3.6.1.4.1.13712
   OBJECT IDENTIFIER
   ::= { enterprises 13712 }

arincSwift                                -- 1.3.6.1.4.1.13712.781
   MODULE-IDENTITY
   LAST-UPDATED "200708081800Z"           -- August 08th, 2007 at 18:00 GMT
   ORGANIZATION "
      Honico Technology GmbH
      on behalf of
      Airbus Deutschland GmbH"
   CONTACT-INFO "
      Dipl. Ing. (FH) Manfred Benten
         Honico Technology GmbH
         Hopfensack 19
         D-20457 Hamburg (GERMANY)
      on behalf of
         Airbus Deutschland GmbH
         BCEYA1 - Cabin Network System Definitions
         Kreetslag 10
         D-21129 Hamburg (GERMANY)
         Phone: +49 40 743 89809
         Mail:  Manfred.Benten@airbus.com"
   DESCRIPTION "
      This MIB is to define the data items used by an arinc 781 conform
      Swift 64 and/or SwiftBradband satcom SDU."
   REVISION     "200706061400Z"
   DESCRIPTION  "
      Initial Version"
   REVISION     "200708081800Z"
   DESCRIPTION  "
      Updates accroding to the ARINC-AGCS working group session held in Annapolis(MD)
      USA from July 10th to July 12th 2007."
   ::= { aeec 781 }

---------------------------------------------------------------------------------------
--                                                                                   --
-- Type definitions                                                                  --
--                                                                                   --
---------------------------------------------------------------------------------------
ASHealthState
::= INTEGER
{
   pass(1),                 -- The system is working.
   fail(2),                 -- The system has an error.
   absent(3)                -- The system is not reachable.
}

ASTestState
::= INTEGER
{
   pass(1),                 -- The test was successfully finished.
   fail(2),                 -- The test was stopped with an error.
   ongoing(3),              -- The test is still running.
   aborted(4)               -- The test was stopped before it had a chance to
                            -- complete.
}

ASLinkState
::= INTEGER
{
   up(1),                   -- Link is working correct and in use
   down(2),                 -- Link is working correct but down
   unconnected(3),          -- No cable is plugged to the port
   errorHW(4)               -- Link has an hardware error
}

ASSatLockState
::= INTEGER
{
   inLock(1),               -- This value indicates, that the satcom system is 
                            -- connected to a satellite and correctly decoding received
                            -- data.
   notInLock(2)             -- This value indicates, that the satcom system is
                            -- not connected to a satellite ore that it is connected,
                            -- but is not correctly decoding received data.
}

ASRestartReason
::= INTEGER
{                           --   The system has been reset
   longPowerCut(1),         --   - due to a long power interruption.
   shortPowerCut(2),        --   - due to a short power interruption.
   safetyTest(3),           --   - due to a safety test.
   lruReconfig(4),          --   - due to a reconfiguration.
   dataloadCompl(5),        --   - after a completed data loading process.
   dataloadComplCSW(6),     --   - after a completed data loading process with CSW.
   fpButtonRequest(7),      --   - after pushing a reset button.
   snmpTestRequest(8),      --   - after a Self Test request via SNMP.
   atCommand(9),            --   - after a request per AT command.
   maintEquipSelfTest(10),  --   - after a maintenance equipment self test.
   maintEquipDefSet(11),    --   - after resetting the default settings during a
                            --     maintenance process.
   snmpResetRequest(12),    --   - after a SNMP reset request.
   maintEquipRequest(13),   --   - after a equipment maintenance request.
   osFailDetect(14),        --   - after an operating system failure detection.
   externalDiscrete(15),    --   - after a discrete request.
}

ASUnitThermState
::= INTEGER
{
   normal(1),               -- The unit is working within its normal operational
                            -- temperature.
   overheat(2),             -- The unit is non critical working outside its normal
                            -- operational temperature.
   shutdown(3)              -- The unit is critical working outside its normal
                            -- operational temperature and has to be shutdown.
}

ASAntThermState
::= INTEGER
{
   ok(1),                   -- The antenna works fine
   class1(2),               -- The thermal antenna state is in class1 mode
   class3(3)                -- The thermal antenna state is in class3 mode
}

ASDateTime                  -- This type is a string in accordance with IETF RFC 3339
::= OCTET STRING (SIZE(0 .. 20))

---------------------------------------------------------------------------------------
-- General Arinc Swift branches                                                      --
---------------------------------------------------------------------------------------
asVersion                                 -- 1.3.6.1.4.1.13712.781.1
   OBJECT IDENTIFIER
   ::= { arincSwift 1 }

asLinks                                   -- 1.3.6.1.4.1.13712.781.2
   OBJECT IDENTIFIER
   ::= { arincSwift 2 }

asSystem                                  -- 1.3.6.1.4.1.13712.781.3
   OBJECT IDENTIFIER
   ::= { arincSwift 3 }

asUnits                                   -- 1.3.6.1.4.1.13712.781.4
   OBJECT IDENTIFIER
   ::= { arincSwift 4 }

asUserDefArea                             -- 1.3.6.1.4.1.13712.781.5
   OBJECT IDENTIFIER
   ::= { arincSwift 5 }

---------------------------------------------------------------------------------------
-- asVersion branch definition                                                       --
---------------------------------------------------------------------------------------
asvMajorVersion                           -- 1.3.6.1.4.1.13712.781.1.1
   OBJECT-TYPE
   SYNTAX Integer32
   MAX-ACCESS read-only
   STATUS current
   DESCRIPTION "
      This object defines the major version of the arincSwift MIB definition.
      The current major version number is 1."
   DEFVAL { 1 }
   ::= { asVersion 1 }

asvMinorVersion                           -- 1.3.6.1.4.1.13712.781.1.2
   OBJECT-TYPE
   SYNTAX Integer32 (0 .. 99)
   MAX-ACCESS read-only
   STATUS current
   DESCRIPTION "
      This object defines the minor version of the arincSwift MIB definition.
      The current minor version number is 0."
   DEFVAL { 0 }
   ::= { asVersion 2 }

---------------------------------------------------------------------------------------
-- asLinks branch definition                                                         --
--    aslServices sub branch definition                                              --
---------------------------------------------------------------------------------------
aslServices                               -- 1.3.6.1.4.1.13712.781.2.1
   OBJECT IDENTIFIER
   ::= { asLinks 1 }

aslsServiceNumbers                        -- 1.3.6.1.4.1.13712.781.2.1.1
   OBJECT-TYPE
   SYNTAX Integer32 (0 .. 100)
   MAX-ACCESS read-only
   STATUS current
   DESCRIPTION "
      This objet indicates the number of entries in the aslsServiceTable and has a
      range from 0 to 100."
   ::= { aslServices 1 }

aslsTable                                 -- 1.3.6.1.4.1.13712.781.2.1.2
   OBJECT-TYPE
   SYNTAX SEQUENCE OF ASLSEntry
   MAX-ACCESS not-accessible
   STATUS current
   DESCRIPTION "
      A list of all available satellite services, which can be offered by the SDU.
      The number of entries is given by the value of satServiceNumber."
   ::= { aslServices 2 }


aslsEntry                                 -- 1.3.6.1.4.1.13712.781.2.1.2.1
   OBJECT-TYPE
   SYNTAX ASLSEntry
   MAX-ACCESS not-accessible
   STATUS current
   DESCRIPTION "
      Colmns of the aslsTable."
   INDEX { aslsIndex }
   ::= { aslsTable 1 }

ASLSEntry ::=
   SEQUENCE {
      aslsIndex             Integer32,
      aslsName              DisplayString,
      aslsInUse             Integer32,
      aslsAvailable         Integer32,
      aslsMaxChannels       Integer32,
      aslsMaxBWPerChannel   Integer32,
      aslsMaxBW             Integer32
   }

aslsIndex                                 -- 1.3.6.1.4.1.13712.781.2.1.2.1.1
   OBJECT-TYPE
   SYNTAX Integer32 (1 .. 32767)
   MAX-ACCESS read-only
   STATUS current
   DESCRIPTION "
      This column contains a unique identifier for this entry."
   ::= { aslsEntry 1 }

aslsName                                  -- 1.3.6.1.4.1.13712.781.2.1.2.1.2
   OBJECT-TYPE
   SYNTAX DisplayString (SIZE(0 .. 63))
   MAX-ACCESS read-only
   STATUS current
   DESCRIPTION "
      This column contains the name of the service in the following form:
      'Service:Subservice'. These are expected to match the PPPoE Service-Names.
      User-defined services and sub-services will not necessarily be present in this
      table, as it may not be possible to determine their availability."
   ::= { aslsEntry 2 }

aslsInUse                                 -- 1.3.6.1.4.1.13712.781.2.1.2.1.3
   OBJECT-TYPE
   SYNTAX Integer32 (0 .. 127)
   MAX-ACCESS read-only
   STATUS current
   DESCRIPTION "
      Number of instances of this service currently in use."
   ::= { aslsEntry 3 }

aslsAvailable                             -- 1.3.6.1.4.1.13712.781.2.1.2.1.4
   OBJECT-TYPE
   SYNTAX Integer32 (0 .. 127)
   MAX-ACCESS read-only
   STATUS current
   DESCRIPTION "
      Number of instances potentially remaining. Note that number of remaining
      instances are not necessarily max-in_use, as other services may consume
      resources required by this service. Due to system dynamics, there is no
      guarantee that the user will be able to place this many additional calls,
      even if it is alone on the system. This value can be seen as a best-case
      scenario."
   ::= { aslsEntry 4 }

aslsMaxChannels                           -- 1.3.6.1.4.1.13712.781.2.1.2.1.5
   OBJECT-TYPE
   SYNTAX Integer32 (0 .. 127)
   MAX-ACCESS read-only
   STATUS current
   DESCRIPTION "
      This value indicates, how many instances of this service type are maximum
      available. Must be zero for invalid entries.
      Examples:
        - 04 for S64-MISDN,
        - 02 for S64-MPDS,
        - 11 for SBB-streaming with a single channel unit
        - 22 for SBB-streaming with a double channel unit"
   ::= { aslsEntry 5 }

aslsMaxBWPerChannel                       -- 1.3.6.1.4.1.13712.781.2.1.2.1.6
   OBJECT-TYPE
   SYNTAX Integer32 (0 .. 32767)
   UNITS "kbps"
   MAX-ACCESS read-only
   STATUS current
   DESCRIPTION "
      This value indicates the maximum bandwidth available on one instance of this
      service."
   ::= { aslsEntry 6 }

aslsMaxBW                                 -- 1.3.6.1.4.1.13712.781.2.1.2.1.7
   OBJECT-TYPE
   SYNTAX Integer32 (0 .. 32767)
   UNITS "kbps"
   MAX-ACCESS read-only
   STATUS current
   DESCRIPTION "
      This value indicates the maximum bandwidth available to all instances of this
      service."
   ::= { aslsEntry 7 }

---------------------------------------------------------------------------------------
-- asLinks branch definition                                                         --
--    aslInfos sub branch definition                                                 --
---------------------------------------------------------------------------------------
aslInfos                                  -- 1.3.6.1.4.1.13712.781.2.2
   OBJECT IDENTIFIER
   ::= { asLinks 2 }

asliSatState                              -- 1.3.6.1.4.1.13712.781.2.2.1
   OBJECT-TYPE
   SYNTAX ASSatLockState
   MAX-ACCESS read-only
   STATUS current
   DESCRIPTION "
      This object shows, if the satellite is locked or not. The type is an enumerated
      integer value."
   ::= { aslInfos 1 }

asliSatID                                 -- 1.3.6.1.4.1.13712.781.2.2.2
   OBJECT-TYPE
   SYNTAX DisplayString (SIZE(0 .. 32))
   MAX-ACCESS read-only
   STATUS current
   DESCRIPTION "
      This object shows, which satellite is connected by the satcom system
      (e.g. 'IOR')"
   ::= { aslInfos 2 }

asliSatIDNum                              -- 1.3.6.1.4.1.13712.781.2.2.3
   OBJECT-TYPE
   SYNTAX Integer32 (0 .. 63)
   MAX-ACCESS read-only
   STATUS current
   DESCRIPTION "
      Unique numeric identifier for the connected satellite."
   ::= { aslInfos 3 }

asliActLinkEntryNumbers                   -- 1.3.6.1.4.1.13712.781.2.2.4
   OBJECT-TYPE
   SYNTAX Integer32 (0 .. 50)
   MAX-ACCESS read-only
   STATUS current
   DESCRIPTION "
      This object indicates the number of the entries in the Active Link Table."
   ::= { aslInfos  4 }

---------------------------------------------------------------------------------------
-- Objects related to the table for the actual used links 'asliActLinkTable'         --
---------------------------------------------------------------------------------------
asliActLinkTable                          -- 1.3.6.1.4.1.13712.781.2.2.5
   OBJECT-TYPE
   SYNTAX SEQUENCE OF ASLIActLinkEntry
   MAX-ACCESS not-accessible
   STATUS current
   DESCRIPTION "
      Table provides details of each connection within the overall satellite link."
   ::= { aslInfos 5 }

asliActLinkEntry                          -- 1.3.6.1.4.1.13712.781.2.2.5.1
   OBJECT-TYPE
   SYNTAX ASLIActLinkEntry
   MAX-ACCESS not-accessible
   STATUS current
   DESCRIPTION "
      Table entry holding parameters per satellite link."
   INDEX { asliActLinkIndex }
   ::= { asliActLinkTable 1 }

ASLIActLinkEntry
   ::= SEQUENCE {
      asliActLinkIndex            Integer32,        -- 01
      asliActLinkReleaseType      Integer32,        -- 02
      asliActLinkReleaseReason    DisplayString,    -- 03
      asliActLinkStatus           ASLinkState,      -- 04
      asliActLinkChanNo           Integer32,        -- 05
      asliActLinkContextID        Integer32,        -- 06
      asliActLinkActualContextID  Integer32,        -- 97
      asliActLinkConnectionID     DisplayString,    -- 08
      asliActLinkNegotiatedBW     Integer32,        -- 09
      asliActLinkIpAddress        IpAddress,        -- 10
      asliActLinkTxTrafficVol     Integer32,        -- 11
      asliActLinkRxTrafficVol     Integer32,        -- 12
      asliActLinkBeamID           Integer32,        -- 13
      asliActLinkSigQual          Integer32,        -- 14
      asliActLinkMaxSigQual       Integer32,        -- 15
      asliActLinkMainIndex        Integer32,        -- 16
      asliActLinkServiceIndex     Integer32,        -- 17
      asliActLinkContrIntefIndex  Integer32,        -- 18
      asliActLinkPhysIntefIndex   Integer32,        -- 19
      asliActLinkStartTime        ASDateTime,       -- 22
      asliActLinkEndTime          ASDateTime,       -- 21
      asliActLinkPPPoEID          Integer32,        -- 22
      asliActLinkQueueTotalSize   Integer32,        -- 23
      asliActLinkQueueFreeSize    Integer32         -- 24
   }

asliActLinkIndex                          -- 1.3.6.1.4.1.13712.781.2.2.5.1.1
   OBJECT-TYPE
   SYNTAX Integer32 (0 .. 32767)
   MAX-ACCESS read-only
   STATUS current
   DESCRIPTION "
      This object is a unique identifier for the current link entry. With each new
      link, this number is to be incremented by one, wrapping around (but avoiding
      conflicts)."
   ::= { asliActLinkEntry 1 }

asliActLinkReleaseType                    -- 1.3.6.1.4.1.13712.781.2.2.5.1.2
   OBJECT-TYPE
   SYNTAX Integer32
   MAX-ACCESS read-only
   STATUS current
   DESCRIPTION "
      This object shows the release type of the current link as numeric codes as
      described in Arinc 781 - Attachment 5, Section 6."
   ::= { asliActLinkEntry 2 }

asliActLinkReleaseReason                  -- 1.3.6.1.4.1.13712.781.2.2.5.1.3
   OBJECT-TYPE
   SYNTAX DisplayString (SIZE(0 .. 128))
   MAX-ACCESS read-only
   STATUS current
   DESCRIPTION "
      This object shows the reason for the release type in a displayable form."
   ::= { asliActLinkEntry 3 }

asliActLinkStatus                         -- 1.3.6.1.4.1.13712.781.2.2.5.1.4
   OBJECT-TYPE
   SYNTAX ASLinkState
   MAX-ACCESS read-only
   STATUS current
   DESCRIPTION "
      This object shows, if the current link is up or not."
   ::= { asliActLinkEntry 4 }

asliActLinkChanNo                         -- 1.3.6.1.4.1.13712.781.2.2.5.1.5
   OBJECT-TYPE
   SYNTAX Integer32 (0 .. 31)
   MAX-ACCESS read-only
   STATUS current
   DESCRIPTION "
      This object shows, which channel is used on the card by the current link."
   DEFVAL { 1 }
   ::= { asliActLinkEntry 5 }

asliActLinkContextID                      -- 1.3.6.1.4.1.13712.781.2.2.5.1.6
   OBJECT-TYPE
   SYNTAX Integer32 (0 .. 255)
   MAX-ACCESS read-only
   STATUS current
   DESCRIPTION "
      In case of a SBB link, this object shows which context ID is assigned to this
      link. If the current link is a swift 64 link, this entry has to be set to zero.
      These are virtual (logical) context ID specific to that user session (tied to a
      primary PDP). The first primary always has ID 1. For detailed information to
      the virtual context IDs refer to Arinc 781 - Attachement 5 - Section 4.2.2.1."
   DEFVAL { 0 }
   ::= { asliActLinkEntry 6 }

asliActLinkActualContextID                -- 1.3.6.1.4.1.13712.781.2.2.5.1.7
   OBJECT-TYPE
   SYNTAX Integer32 (0 .. 11)
   MAX-ACCESS read-only
   STATUS current
   DESCRIPTION "
      The context ID used over the air. This ID has to be unique per channel card in
      the system. A zero indicates that the actual entry is not mapped to an PDP
      context (e.g. in case of S64 link)."
   DEFVAL { 0 }
   ::= { asliActLinkEntry 7 }

asliActLinkConnectionID                   -- 1.3.6.1.4.1.13712.781.2.2.5.1.8
   OBJECT-TYPE
   SYNTAX DisplayString (SIZE(0 .. 128))
   MAX-ACCESS read-only
   STATUS current
   DESCRIPTION "
      This object shows information about the connection (e.g. initialization string
      of the current link in form of the used AT command). If the original string was
      longer than can fit in this field, it will be truncated."
   ::= { asliActLinkEntry 8 }

asliActLinkNegotiatedBW                   -- 1.3.6.1.4.1.13712.781.2.2.5.1.9
   OBJECT-TYPE
   SYNTAX Integer32 (0 .. 500)
   UNITS "kbps"
   MAX-ACCESS read-only
   STATUS current
   DESCRIPTION "
      This object shows the currently negotiated bandwidth of the link in this table
      entry."
   ::= { asliActLinkEntry 9 }

asliActLinkIpAddress                      -- 1.3.6.1.4.1.13712.781.2.2.5.1.10
   OBJECT-TYPE
   SYNTAX IpAddress
   MAX-ACCESS read-only
   STATUS current
   DESCRIPTION "
      This object contains the IP-Address of the current link. If this link is a
      sub-link of another entry, which does not have an own IP address (e.g. a part
      of a bundle or a secondary context), this field has to contain the address of
      the primary context it is related to."
   DEFVAL { ''h }
   ::= { asliActLinkEntry 10 }

asliActLinkTxTrafficVol                   -- 1.3.6.1.4.1.13712.781.2.2.5.1.11
   OBJECT-TYPE
   SYNTAX Integer32
   UNITS "kBytes"
   MAX-ACCESS read-only
   STATUS current
   DESCRIPTION "
      This object contains the information about the total transmitted bytes over
      this link in kBytes. If the info is not available, the value must be -1."
   DEFVAL { 0 }
   ::= { asliActLinkEntry 11 }

asliActLinkRxTrafficVol                   -- 1.3.6.1.4.1.13712.781.2.2.5.1.12
   OBJECT-TYPE
   SYNTAX Integer32
   UNITS "kBytes"
   MAX-ACCESS read-only
   STATUS current
   DESCRIPTION "
      This object contains the information about the total received bytes over this
      link in kBytes. If this information is not available, the value must be -1."
   DEFVAL { 0 }
   ::= { asliActLinkEntry 12 }

asliActLinkBeamID                         -- 1.3.6.1.4.1.13712.781.2.2.5.1.13
   OBJECT-TYPE
   SYNTAX Integer32
   MAX-ACCESS read-only
   STATUS current
   DESCRIPTION "
      This object shows, which spot beam is connected by the current link."
   ::= { asliActLinkEntry 13 }

asliActLinkSigQual                        -- 1.3.6.1.4.1.13712.781.2.2.5.1.14
   OBJECT-TYPE
   SYNTAX Integer32
   UNITS "dBHz * 10"
   MAX-ACCESS read-only
   STATUS current
   DESCRIPTION "
      This object shows the Quality in dBHz*10 of the current link."
   ::= { asliActLinkEntry 14 }

asliActLinkMaxSigQual                     -- 1.3.6.1.4.1.13712.781.2.2.5.1.15
   OBJECT-TYPE
   SYNTAX Integer32
   UNITS "dBHz * 10"
   MAX-ACCESS read-only
   STATUS current
   DESCRIPTION "
      Expected Maximum/ideal values for Link Signal Quality."
   ::= { asliActLinkEntry 15 }

asliActLinkMainIndex                      -- 1.3.6.1.4.1.13712.781.2.2.5.1.16
   OBJECT-TYPE
   SYNTAX Integer32
   MAX-ACCESS read-only
   STATUS current
   DESCRIPTION "
      If this link entry is part of bundle (e.g. a secondary context), this object
      refers the main entry (e.g. the primary context) in this table to which this
      subentry is related."
   ::= { asliActLinkEntry 16 }

asliActLinkServiceIndex                   -- 1.3.6.1.4.1.13712.781.2.2.5.1.17
   OBJECT-TYPE
   SYNTAX Integer32
   MAX-ACCESS read-only
   STATUS current
   DESCRIPTION "
      This object is a link to the Service Table by referring the used Service. For
      links not related to an PPPoE service, this value is 0."
   ::= { asliActLinkEntry 17 }

asliActLinkContrIntefIndex                -- 1.3.6.1.4.1.13712.781.2.2.5.1.18
   OBJECT-TYPE
   SYNTAX Integer32
   MAX-ACCESS read-only
   STATUS current
   DESCRIPTION "
      This object contains the index number of the PPP control interface, which is
      related to this link. It is a crosslink into the pppLinkStatusTable of the
      PPP-LCP-MIB by referring the value of the according pppLinkStatusPhysicalIndex.
      For links not related to PPP connections (voice calls, for example), this value
      is 0. Also zero for secondary PDPs."
   ::= { asliActLinkEntry 18 }

asliActLinkPhysIntefIndex                 -- 1.3.6.1.4.1.13712.781.2.2.5.1.19
   OBJECT-TYPE
   SYNTAX Integer32
   MAX-ACCESS read-only
   STATUS current
   DESCRIPTION "
      This object contains the index number of the physical interface, where this link
      is related to. The value is a crosslink into the ifTable of the RFC1213-MIB by
      referring the according value ifIndex. For links not related to an IP interface
      (analog POTS, for example), this value is 0."
   ::= { asliActLinkEntry 19 }

asliActLinkStartTime                      -- 1.3.6.1.4.1.13712.781.2.2.5.1.20
   OBJECT-TYPE
   SYNTAX ASDateTime
   MAX-ACCESS read-only
   STATUS current
   DESCRIPTION "
      Time at which the link was brought up."
   ::= { asliActLinkEntry 20 }

asliActLinkEndTime                        -- 1.3.6.1.4.1.13712.781.2.2.5.1.21
   OBJECT-TYPE
   SYNTAX ASDateTime
   MAX-ACCESS read-only
   STATUS current
   DESCRIPTION "
      Time at which the link was brought down. If the link is still connected
      this field has to contain the same value as the start time."
   ::= { asliActLinkEntry 21 }

asliActLinkPPPoEID                        -- 1.3.6.1.4.1.13712.781.2.2.5.1.22
   OBJECT-TYPE
   SYNTAX Integer32
   MAX-ACCESS read-only
   STATUS current
   DESCRIPTION "
      PPPoE Session ID which started the call. For links not started through PPPoE,
      this value is zero. For secondary PDPs, this value is the one from the related
      primary PDP."
   ::= { asliActLinkEntry 22 }

asliActLinkQueueTotalSize                 -- 1.3.6.1.4.1.13712.781.2.2.5.1.23
   OBJECT-TYPE
   SYNTAX Integer32 (-1 .. 2147483647)
   UNITS "Kbytes"
   MAX-ACCESS read-only
   STATUS current
   DESCRIPTION "
      This value defines the queue size for the current air to ground link. It can
      be set to zero if the actual link is a sub link of another entry and has no
      own queue (e.g. a secondary context). This value can be set to -1, if the
      system (e.g. for temporary design reasons) cannot provide. Due to the fact
      that this value is very useful for client applications to calculate the
      throughput the satcom systems shall implement this feature as soon as
      possible."
   ::= { asliActLinkEntry 23 }

asliActLinkQueueFreeSize                  -- 1.3.6.1.4.1.13712.781.2.2.5.1.24
   OBJECT-TYPE
   SYNTAX Integer32 (-1 .. 2147483647)
   UNITS "Kbytes"
   MAX-ACCESS read-only
   STATUS current
   DESCRIPTION "
      This value defines how much space is available in the air to ground queue. This
      value can be set to -1, if the system (e.g. for temporary design reasons) cannot
      provide. Due to the fact that this value is very useful for client applications
      to calculate the throughput the satcom systems shall implement this feature as
      soon as possible."
   ::= { asliActLinkEntry 24 }

---------------------------------------------------------------------------------------
-- End of Table 'asliActLinkTable'                                                   --
---------------------------------------------------------------------------------------
asliHistLinkEntryNumbers                  -- 1.3.6.1.4.1.13712.781.2.2.6
   OBJECT-TYPE
   SYNTAX Integer32
   MAX-ACCESS read-only
   STATUS current
   DESCRIPTION "
      This object indicates the number of the entries in the History Link Table."
   ::= { aslInfos  6 }

---------------------------------------------------------------------------------------
-- Objects related to the table for the history of the links 'asliHistLinkTable'     --
---------------------------------------------------------------------------------------
asliHistLinkTable                         -- 1.3.6.1.4.1.13712.781.2.2.7
   OBJECT-TYPE
   SYNTAX SEQUENCE OF ASLIHistLinkEntry
   MAX-ACCESS not-accessible
   STATUS current
   DESCRIPTION "
      Table provides details of each historical connection within the overall
      satellite link."
   ::= { aslInfos 7 }

asliHistLinkEntry                         -- 1.3.6.1.4.1.13712.781.2.2.7.1
   OBJECT-TYPE
   SYNTAX ASLIHistLinkEntry
   MAX-ACCESS not-accessible
   STATUS current
   DESCRIPTION "
      Table entry holding parameters per satellite link."
   INDEX { asliHistLinkIndex }
   ::= { asliHistLinkTable 1 }

ASLIHistLinkEntry
   ::= SEQUENCE {
      asliHistLinkIndex            Integer32,        -- 01
      asliHistLinkReleaseType      Integer32,        -- 02
      asliHistLinkReleaseReason    DisplayString,    -- 03
      asliHistLinkStatus           ASLinkState,      -- 04
      asliHistLinkChanNo           Integer32,        -- 05
      asliHistLinkContextID        Integer32,        -- 06
      asliHistLinkActualContextID  Integer32,        -- 97
      asliHistLinkConnectionID     DisplayString,    -- 08
      asliHistLinkNegotiatedBW     Integer32,        -- 09
      asliHistLinkIpAddress        IpAddress,        -- 10
      asliHistLinkTxTrafficVol     Integer32,        -- 11
      asliHistLinkRxTrafficVol     Integer32,        -- 12
      asliHistLinkBeamID           Integer32,        -- 13
      asliHistLinkSigQual          Integer32,        -- 14
      asliHistLinkMaxSigQual       Integer32,        -- 15
      asliHistLinkMainIndex        Integer32,        -- 16
      asliHistLinkServiceIndex     Integer32,        -- 17
      asliHistLinkContrIntefIndex  Integer32,        -- 18
      asliHistLinkPhysIntefIndex   Integer32,        -- 19
      asliHistLinkStartTime        ASDateTime,       -- 22
      asliHistLinkEndTime          ASDateTime,       -- 21
      asliHistLinkPPPoEID          Integer32,        -- 22
      asliHistLinkQueueTotalSize   Integer32,        -- 23
      asliHistLinkQueueFreeSize    Integer32         -- 24
   }

asliHistLinkIndex                         -- 1.3.6.1.4.1.13712.781.2.2.7.1.1
   OBJECT-TYPE
   SYNTAX Integer32 (0 .. 32767)
   MAX-ACCESS read-only
   STATUS current
   DESCRIPTION "
      This object is a unique identifier for the history link entry. It is triggert
      from the acual link entry by moving a complete closed entry to the end of this
      table."
   ::= { asliHistLinkEntry 1 }

asliHistLinkReleaseType                   -- 1.3.6.1.4.1.13712.781.2.2.7.1.2
   OBJECT-TYPE
   SYNTAX Integer32
   MAX-ACCESS read-only
   STATUS current
   DESCRIPTION "
      This object contains historical values. For more details see the according
      object in the actual link table."
   ::= { asliHistLinkEntry 2 }

asliHistLinkReleaseReason                 -- 1.3.6.1.4.1.13712.781.2.2.7.1.3
   OBJECT-TYPE
   SYNTAX DisplayString (SIZE(0 .. 128))
   MAX-ACCESS read-only
   STATUS current
   DESCRIPTION "
      This object contains historical values. For more details see the according
      object in the actual link table."
   ::= { asliHistLinkEntry 3 }

asliHistLinkStatus                        -- 1.3.6.1.4.1.13712.781.2.2.7.1.4
   OBJECT-TYPE
   SYNTAX ASLinkState
   MAX-ACCESS read-only
   STATUS current
   DESCRIPTION "
      This object contains historical values. For more details see the according
      object in the actual link table."
   ::= { asliHistLinkEntry 4 }

asliHistLinkChanNo                        -- 1.3.6.1.4.1.13712.781.2.2.7.1.5
   OBJECT-TYPE
   SYNTAX Integer32 (0 .. 31)
   MAX-ACCESS read-only
   STATUS current
   DESCRIPTION "
      This object contains historical values. For more details see the according
      object in the actual link table."
   DEFVAL { 1 }
   ::= { asliHistLinkEntry 5 }

asliHistLinkContextID                     -- 1.3.6.1.4.1.13712.781.2.2.7.1.6
   OBJECT-TYPE
   SYNTAX Integer32 (0 .. 255)
   MAX-ACCESS read-only
   STATUS current
   DESCRIPTION "
      This object contains historical values. For more details see the according
      object in the actual link table."
   DEFVAL { 0 }
   ::= { asliHistLinkEntry 6 }

asliHistLinkActualContextID               -- 1.3.6.1.4.1.13712.781.2.2.7.1.7
   OBJECT-TYPE
   SYNTAX Integer32 (0 .. 11)
   MAX-ACCESS read-only
   STATUS current
   DESCRIPTION "
      This object contains historical values. For more details see the according
      object in the actual link table."
   DEFVAL { 0 }
   ::= { asliHistLinkEntry 7 }

asliHistLinkConnectionID                  -- 1.3.6.1.4.1.13712.781.2.2.7.1.8
   OBJECT-TYPE
   SYNTAX DisplayString (SIZE(0 .. 128))
   MAX-ACCESS read-only
   STATUS current
   DESCRIPTION "
      This object contains historical values. For more details see the according
      object in the actual link table."
   ::= { asliHistLinkEntry 8 }

asliHistLinkNegotiatedBW                  -- 1.3.6.1.4.1.13712.781.2.2.7.1.9
   OBJECT-TYPE
   SYNTAX Integer32 (0 .. 500)
   UNITS "kBits/sec"
   MAX-ACCESS read-only
   STATUS current
   DESCRIPTION "
      This object contains historical values. For more details see the according
      object in the actual link table."
   ::= { asliHistLinkEntry 9 }

asliHistLinkIpAddress                     -- 1.3.6.1.4.1.13712.781.2.2.7.1.10
   OBJECT-TYPE
   SYNTAX IpAddress
   MAX-ACCESS read-only
   STATUS current
   DESCRIPTION "
      This object contains historical values. For more details see the according
      object in the actual link table."
   DEFVAL { ''h }
   ::= { asliHistLinkEntry 10 }

asliHistLinkTxTrafficVol                  -- 1.3.6.1.4.1.13712.781.2.2.7.1.11
   OBJECT-TYPE
   SYNTAX Integer32
   UNITS "kBytes"
   MAX-ACCESS read-only
   STATUS current
   DESCRIPTION "
      This object contains historical values. For more details see the according
      object in the actual link table."
   DEFVAL { 0 }
   ::= { asliHistLinkEntry 11 }

asliHistLinkRxTrafficVol                  -- 1.3.6.1.4.1.13712.781.2.2.7.1.12
   OBJECT-TYPE
   SYNTAX Integer32
   UNITS "kBytes"
   MAX-ACCESS read-only
   STATUS current
   DESCRIPTION "
      This object contains historical values. For more details see the according
      object in the actual link table."
   DEFVAL { 0 }
   ::= { asliHistLinkEntry 12 }

asliHistLinkBeamID                        -- 1.3.6.1.4.1.13712.781.2.2.7.1.13
   OBJECT-TYPE
   SYNTAX Integer32
   MAX-ACCESS read-only
   STATUS current
   DESCRIPTION "
      This object contains historical values. For more details see the according
      object in the actual link table."
   ::= { asliHistLinkEntry 13 }

asliHistLinkSigQual                       -- 1.3.6.1.4.1.13712.781.2.2.7.1.14
   OBJECT-TYPE
   SYNTAX Integer32
   UNITS "dBHz * 10"
   MAX-ACCESS read-only
   STATUS current
   DESCRIPTION "
      This object contains historical values. For more details see the according
      object in the actual link table."
   ::= { asliHistLinkEntry 14 }

asliHistLinkMaxSigQual                    -- 1.3.6.1.4.1.13712.781.2.2.7.1.15
   OBJECT-TYPE
   SYNTAX Integer32
   UNITS "dBHz * 10"
   MAX-ACCESS read-only
   STATUS current
   DESCRIPTION "
      This object contains historical values. For more details see the according
      object in the actual link table."
   ::= { asliHistLinkEntry 15 }

asliHistLinkMainIndex                     -- 1.3.6.1.4.1.13712.781.2.2.7.1.16
   OBJECT-TYPE
   SYNTAX Integer32
   MAX-ACCESS read-only
   STATUS current
   DESCRIPTION "
      This object contains historical values. For more details see the according
      object in the actual link table."
   ::= { asliHistLinkEntry 16 }


asliHistLinkServiceIndex                  -- 1.3.6.1.4.1.13712.781.2.2.7.1.17
   OBJECT-TYPE
   SYNTAX Integer32
   MAX-ACCESS read-only
   STATUS current
   DESCRIPTION "
      This object contains historical values. For more details see the according
      object in the actual link table."
   ::= { asliHistLinkEntry 17 }

asliHistLinkContrIntefIndex               -- 1.3.6.1.4.1.13712.781.2.2.7.1.18
   OBJECT-TYPE
   SYNTAX Integer32
   MAX-ACCESS read-only
   STATUS current
   DESCRIPTION "
      This object contains historical values. For more details see the according
      object in the actual link table."
   ::= { asliHistLinkEntry 18 }

asliHistLinkPhysIntefIndex                -- 1.3.6.1.4.1.13712.781.2.2.7.1.19
   OBJECT-TYPE
   SYNTAX Integer32
   MAX-ACCESS read-only
   STATUS current
   DESCRIPTION "
      This object contains historical values. For more details see the according
      object in the actual link table."
   ::= { asliHistLinkEntry 19 }

asliHistLinkStartTime                     -- 1.3.6.1.4.1.13712.781.2.2.7.1.20
   OBJECT-TYPE
   SYNTAX ASDateTime
   MAX-ACCESS read-only
   STATUS current
   DESCRIPTION "
      This object contains historical values. For more details see the according
      object in the actual link table."
   ::= { asliHistLinkEntry 20 }

asliHistLinkEndTime                       -- 1.3.6.1.4.1.13712.781.2.2.7.1.21
   OBJECT-TYPE
   SYNTAX ASDateTime
   MAX-ACCESS read-only
   STATUS current
   DESCRIPTION "
      This object contains historical values. For more details see the according
      object in the actual link table."
   ::= { asliHistLinkEntry 21 }

asliHistLinkPPPoEID                       -- 1.3.6.1.4.1.13712.781.2.2.7.1.22
   OBJECT-TYPE
   SYNTAX Integer32
   MAX-ACCESS read-only
   STATUS current
   DESCRIPTION "
      This object contains historical values. For more details see the according
      object in the actual link table."
   ::= { asliHistLinkEntry 22 }

asliHistLinkQueueTotalSize                -- 1.3.6.1.4.1.13712.781.2.2.7.1.23
   OBJECT-TYPE
   SYNTAX Integer32 (-1 .. 32767)
   UNITS "Kbytes"
   MAX-ACCESS read-only
   STATUS current
   DESCRIPTION "
      This object contains historical values. For more details see the according
      object in the actual link table."
   ::= { asliHistLinkEntry 23 }

asliHistLinkQueueFreeSize                 -- 1.3.6.1.4.1.13712.781.2.2.7.1.24
   OBJECT-TYPE
   SYNTAX Integer32 (-1 .. 32767)
   UNITS "Kbytes"
   MAX-ACCESS read-only
   STATUS current
   DESCRIPTION "
      This object contains historical values. For more details see the according
      object in the actual link table."
   ::= { asliHistLinkEntry 24 }

---------------------------------------------------------------------------------------
-- End of Table 'asliHistLinkTable'                                                  --
---------------------------------------------------------------------------------------
asliSatHandoverPending                    -- 1.3.6.1.4.1.13712.781.2.2.8
   OBJECT-TYPE
   SYNTAX TruthValue
   MAX-ACCESS read-only
   STATUS current
   DESCRIPTION "
      Set if the system believes it will need to do a handover soon."
   ::= { aslInfos 8 }

asliSatNetworkName                        -- 1.3.6.1.4.1.13712.781.2.2.9
   OBJECT-TYPE
   SYNTAX DisplayString (SIZE(0 .. 16))
   MAX-ACCESS read-only
   STATUS current
   DESCRIPTION "
      This object indicates to which satellite network the SDU is connected, because
      the satellite identification numbers may not be unique between the different
      networks (I3 and I4) Possible values should be for example 'GAN' for I3 and
      'BGAN' for I4."
   ::= { aslInfos 9 }

---------------------------------------------------------------------------------------
-- asSystem branch definition                                                        --
--    assConfig sub branch definition                                                --
---------------------------------------------------------------------------------------
assConfig                                 -- 1.3.6.1.4.1.13712.781.3.1
   OBJECT IDENTIFIER
   ::= { asSystem 1 }

asscTrapDest                              -- 1.3.6.1.4.1.13712.781.3.1.1
   OBJECT-TYPE
   SYNTAX IpAddress
   MAX-ACCESS read-write
   STATUS current
   DESCRIPTION "
      A client can define the destination of the traps by setting this object to the
      expected address. The default value of this entry is 0.0.0.0, indicating no
      client."
   DEFVAL { '00000000'h }
   ::= { assConfig 1 }

asscTrapDestPort                          -- 1.3.6.1.4.1.13712.781.3.1.2
   OBJECT-TYPE
   SYNTAX Integer32 (0 .. 65535)
   MAX-ACCESS read-write
   STATUS current
   DESCRIPTION "
      A client can define the destination port on which the traps are expected. The
      standard SNMP Trap port is 162, but any other can be used. The default value
      is 0."
   ::= { assConfig 2 }
---------------------------------------------------------------------------------------
-- asSystem branch definition                                                        --
--    assInfos sub branch definition                                                 --
---------------------------------------------------------------------------------------
assInfos                                  -- 1.3.6.1.4.1.13712.781.3.2
   OBJECT IDENTIFIER
   ::= { asSystem 2 }

assiHealthStatus                          -- 1.3.6.1.4.1.13712.781.3.2.1
   OBJECT-TYPE
   SYNTAX ASHealthState
   MAX-ACCESS read-only
   STATUS current
   DESCRIPTION "
      This object shows the health state of the whole system."
   ::= { assInfos 1 }

assiVendor                                -- 1.3.6.1.4.1.13712.781.3.2.2
   OBJECT-TYPE
   SYNTAX DisplayString (SIZE(0 .. 64))
   MAX-ACCESS read-only
   STATUS current
   DESCRIPTION "
      This object contains information about the system vendor."
   ::= { assInfos 2 }

assiHWPN                                  -- 1.3.6.1.4.1.13712.781.3.2.3
   OBJECT-TYPE
   SYNTAX DisplayString (SIZE(0 .. 32))
   MAX-ACCESS read-only
   STATUS current
   DESCRIPTION "
      This object contains the hardware part number."
   ::= { assInfos 3 }

assiSerialNumber                          -- 1.3.6.1.4.1.13712.781.3.2.4
   OBJECT-TYPE
   SYNTAX DisplayString (SIZE(0 .. 32))
   MAX-ACCESS read-only
   STATUS current
   DESCRIPTION "
      This object contains the serial number of the system."
   ::= { assInfos 4 }

assiHWFunction                            -- 1.3.6.1.4.1.13712.781.3.2.5
   OBJECT-TYPE
   SYNTAX DisplayString (SIZE(0 .. 32))
   MAX-ACCESS read-only
   STATUS current
   DESCRIPTION "
      This object contains a string to describe the general hardware function (e.g.
      'High Speed SBB Satellite Modem')."
   ::= { assInfos 5 }

assiShortName                             -- 1.3.6.1.4.1.13712.781.3.2.6
   OBJECT-TYPE
   SYNTAX DisplayString (SIZE(0 .. 16))
   MAX-ACCESS read-only
   STATUS current
   DESCRIPTION "
      This object contains a short name (e.g. 'HS720')."
   ::= { assInfos 6 }



---------------------------------------------------------------------------------------
-- asSystem branch definition                                                        --
--    assTraps sub branch definition                                                 --
---------------------------------------------------------------------------------------
assTraps                                  -- 1.3.6.1.4.1.13712.781.3.3
   OBJECT IDENTIFIER
   ::= { asSystem 3 }

asstHealthStatusTrap                      -- 1.3.6.1.4.1.13712.781.3.3.1
   NOTIFICATION-TYPE
   OBJECTS {
      assiHealthStatus
   }
   STATUS current
   DESCRIPTION "
      This trap has to be sent, if the health status of the system changes."
   ::= { assTraps 1 }

asstLinkSatusTrap                         -- 1.3.6.1.4.1.13712.781.3.3.2
   NOTIFICATION-TYPE
   OBJECTS {
      asliActLinkIndex, asliActLinkReleaseType, asliActLinkStatus
   }
   STATUS current
   DESCRIPTION "
      This trap has to be sent, if one of the objects related to the Link status
      changes. If the satcom system changes more than one object within 1 second,
      it may only send the trap once."
   ::= { assTraps 2 }

asstLinkBeamIDTrap                        -- 1.3.6.1.4.1.13712.781.3.3.3
   NOTIFICATION-TYPE
   OBJECTS {
      asliSatID, asliActLinkIndex, asliActLinkBeamID, asliSatState
   }
   STATUS current
   DESCRIPTION "
      This trap has to be sent, if the system changes the beam or the satellite.
      It has also to be sent, if the lock state changes."
   ::= { assTraps 3 }

asstServiceAvailabilityTrap               -- 1.3.6.1.4.1.13712.781.3.3.4
   NOTIFICATION-TYPE
   OBJECTS {
      aslsIndex, aslsAvailable
   }
   STATUS current
   DESCRIPTION "
      This trap has to be sent,  if the availability status of a service changes
      in the service table."
   ::= { assTraps 4 }

asstLinkInsertedTrap                      -- 1.3.6.1.4.1.13712.781.3.3.5
   NOTIFICATION-TYPE
   OBJECTS {
      asliActLinkIndex
   }
   STATUS current
   DESCRIPTION "
      This trap has to be sent, when the system inserts a new entry into the link
      table."
   ::= { assTraps 5 }

asstLinkRemovedTrap                       -- 1.3.6.1.4.1.13712.781.3.3.6
   NOTIFICATION-TYPE
   OBJECTS {
      asliActLinkIndex
   }
   STATUS current
   DESCRIPTION "
      This trap has to be sent, if the timer for the deletion of a link table entry
      has expired. After this trap, the according entry has been moved to the link
      table."
   ::= { assTraps 6 }

asstSatHandoverPending                    -- 1.3.6.1.4.1.13712.781.3.3.7
   NOTIFICATION-TYPE
   OBJECTS {
      asliSatHandoverPending
   }
   STATUS current
   DESCRIPTION "
      This trap will be sent if the system knows it may need to do a handover soon."
   ::= { assTraps 7 }


---------------------------------------------------------------------------------------
-- asSystem branch definition                                                        --
--    assSelfTest sub branch definition                                              --
---------------------------------------------------------------------------------------
assSelfTestAvailable                      -- 1.3.6.1.4.1.13712.781.3.4
   OBJECT-TYPE
   SYNTAX TruthValue
   MAX-ACCESS read-only
   STATUS current
   DESCRIPTION "
      True, if the system is supporting selftet functions.
      Otherwise selftests will not be supported."
   ::= { asSystem 4 }

assSelfTest                               -- 1.3.6.1.4.1.13712.781.3.5
   OBJECT IDENTIFIER
   ::= { asSystem 5 }

asssTestCaseNumber                        -- 1.3.6.1.4.1.13712.781.3.5.1
   OBJECT-TYPE
   SYNTAX Integer32 (0 .. 100)
   MAX-ACCESS read-only
   STATUS current
   DESCRIPTION "
      This object indicates how many entries are in the test case table."
   ::= { assSelfTest 1 }

---------------------------------------------------------------------------------------
-- Objects related to the table for test cases 'asssTestcaseTable'                   --
---------------------------------------------------------------------------------------
asssTestcaseTable                         -- 1.3.6.1.4.1.13712.781.3.5.2
   OBJECT-TYPE
   SYNTAX SEQUENCE OF ASSSTestcaseEntry
   MAX-ACCESS not-accessible
   STATUS current
   DESCRIPTION "
      Table provides the supported test cases."
   ::= { assSelfTest 2 }

asssTestcaseEntry                         -- 1.3.6.1.4.1.13712.781.3.5.2.1
   OBJECT-TYPE
   SYNTAX ASSSTestcaseEntry
   MAX-ACCESS not-accessible
   STATUS current
   DESCRIPTION "
      Table entry holding parameters per test case."
   INDEX { asssTestCaseIndex }
   ::= { asssTestcaseTable 1 }

ASSSTestcaseEntry
   ::= SEQUENCE {
      asssTestCaseIndex            Integer32,        -- 01
      asssTestCaseName             DisplayString     -- 02
   }

asssTestCaseIndex                         -- 1.3.6.1.4.1.13712.781.3.5.2.1.1
   OBJECT-TYPE
   SYNTAX Integer32 (1 .. 100)
   MAX-ACCESS read-only
   STATUS current
   DESCRIPTION "
      This object defines a unique identifier for the according test case."
   ::= { asssTestcaseEntry 1 }

asssTestCaseName                          -- 1.3.6.1.4.1.13712.781.3.5.2.1.2
   OBJECT-TYPE
   SYNTAX DisplayString (SIZE(0 .. 50))
   MAX-ACCESS read-only
   STATUS current
   DESCRIPTION "
      This object shows the name of the test case (e.g. 'Link-Test'). IF the system
      will offer the possibility to reset it via this interface, it has to insert a
      entry with the name 'Reset-System'."
   ::= { asssTestcaseEntry 2 }

---------------------------------------------------------------------------------------
-- End of 'asssTestcaseTable'                                                        --
---------------------------------------------------------------------------------------
asssTestCaseCommand                       -- 1.3.6.1.4.1.13712.781.3.5.3
   OBJECT-TYPE
   SYNTAX Integer32 (0 .. 100)
   MAX-ACCESS read-write
   STATUS current
   DESCRIPTION "
      This is a writable object. By setting this value to a non zero value, the
      corresponding test case of the test case table will be started.  Starting a
      test will stop a previously running one. Setting it to zero will stop any
      running test."
   ::= { assSelfTest 3 }

asssTestUpTime                            -- 1.3.6.1.4.1.13712.781.3.5.4
   OBJECT-TYPE
   SYNTAX TimeTicks
   MAX-ACCESS read-write
   STATUS current
   DESCRIPTION "
      This is a writable object. A client application can control the run time of the
      test case."
   ::= { assSelfTest 4 }

asssTestStatus                            -- 1.3.6.1.4.1.13712.781.3.5.5
   OBJECT-TYPE
   SYNTAX ASTestState
   MAX-ACCESS read-only
   STATUS current
   DESCRIPTION "
      This value shows the status of the current running self test."
   ::= { assSelfTest 5 }

asssTestLastResult                        -- 1.3.6.1.4.1.13712.781.3.5.6
   OBJECT-TYPE
   SYNTAX ASTestState
   MAX-ACCESS read-only
   STATUS current
   DESCRIPTION "
      This value indicates the result of the last finished test."
   ::= { assSelfTest 6 }

asssTestReturnCode                        -- 1.3.6.1.4.1.13712.781.3.5.7
   OBJECT-TYPE
   SYNTAX Integer32
   MAX-ACCESS read-only
   STATUS current
   DESCRIPTION "
      This field covers a unique return code of the self test, which can easily be
      validated."
   ::= { assSelfTest 7 }

asssTestReturnMessage                     -- 1.3.6.1.4.1.13712.781.3.5.8
   OBJECT-TYPE
   SYNTAX DisplayString (SIZE(0 .. 255))
   MAX-ACCESS read-only
   STATUS current
   DESCRIPTION "
      This field contains a textual result message of the last self test, which can
      be logged."
   ::= { assSelfTest 8 }

---------------------------------------------------------------------------------------
-- asUnits branch definition                                                         --
--    asuSDU sub branch definition                                                   --
---------------------------------------------------------------------------------------
asuSDUAvailable                           -- 1.3.6.1.4.1.13712.781.4.1
   OBJECT-TYPE
   SYNTAX TruthValue
   MAX-ACCESS read-only
   STATUS current
   DESCRIPTION "
      This object is has to set to true, if the system is supporting detailed SDU
      relevant information. Otherwise SDU relavant detail information will not be
      supported."
   ::= { asUnits 1 }

asuSDU                                    -- 1.3.6.1.4.1.13712.781.4.2
   OBJECT IDENTIFIER
   ::= { asUnits 2 }

---------------------------------------------------------------------------------------
-- asUnits branch definition                                                         --
--    asuSDU sub branch definition                                                   --
--       asuSDUInfo sub sub branch definition                                        --
---------------------------------------------------------------------------------------
asuSDUInfo                                -- 1.3.6.1.4.1.13712.781.4.2.1
   OBJECT IDENTIFIER
   ::= { asuSDU 1 }

asuSduInfoTableNumbers                    -- 1.3.6.1.4.1.13712.781.4.2.1.1
   OBJECT-TYPE
   SYNTAX Integer32 (1 .. 100)
   MAX-ACCESS read-only
   STATUS current
   DESCRIPTION "
      This object indicates the number of entries in the SDU info table."
   ::= { asuSDUInfo 1 }

---------------------------------------------------------------------------------------
-- Objects related to the table for sdu informations 'asuSduInfoTableTable'          --
---------------------------------------------------------------------------------------
asuSduInfoTable                           -- 1.3.6.1.4.1.13712.781.4.2.1.2
   OBJECT-TYPE
   SYNTAX SEQUENCE OF ASUSduInfoEntry
   MAX-ACCESS not-accessible
   STATUS current
   DESCRIPTION "
      This table provides contains details information about each SDU, if supported."
   ::= { asuSDUInfo 2 }

asuSduInfoEntry                           -- 1.3.6.1.4.1.13712.781.4.2.1.2.1
   OBJECT-TYPE
   SYNTAX ASUSduInfoEntry
   MAX-ACCESS not-accessible
   STATUS current
   DESCRIPTION "
      Table entry holding parameters per SDU entry."
   INDEX { asuSduInfoIndex }
   ::= { asuSduInfoTable 1 }

ASUSduInfoEntry
::= SEQUENCE {
      asuSduInfoIndex                Integer32,          -- 01
      asuSduInfoVendor               DisplayString,      -- 02
      asuSduInfoHWPN                 DisplayString,      -- 03
      asuSduInfoSN                   DisplayString,      -- 04
      asuSduInfoHWFunction           DisplayString,      -- 05
      asuSduInfoDesignation          DisplayString,      -- 06
      asuSduInfoSWVersion            DisplayString,      -- 07
      asuSduInfoOverallStatus        ASHealthState,      -- 08
      asuSduInfoPowerOnSelfTest      ASHealthState,      -- 09
      asuSduInfoInteractiveSelfTest  ASHealthState,      -- 10
      asuSduInfoFailureCode          Integer32,          -- 11
      asuSduInfoFailureReason        DisplayString,      -- 12
      asuSduInfoTemperature          Integer32,          -- 13
      asuSduInfoThermState           ASUnitThermState,   -- 14
      asuSduInfoCC1Status            ASHealthState,      -- 15
      asuSduInfoCC2Status            ASHealthState,      -- 16
      asuSduInfoIntHPAState          ASHealthState,      -- 17
      asuSduInfoQuadrax1Status       ASLinkState,        -- 18
      asuSduInfoQuadrax2Status       ASLinkState,        -- 19
      asuSduInfoIRS1BusStatus        ASHealthState,      -- 20
      asuSduInfoIRS1SystemStatus     ASHealthState,      -- 21
      asuSduInfoPSMState             ASHealthState,      -- 22
      asuSduInfoOcxoState            ASHealthState,      -- 23
      asuSduInfoSecureORTStatus      ASHealthState,      -- 24
      asuSduInfoUserORTStatus        ASHealthState,      -- 25
      asuSduInfoStrapsState          TruthValue,         -- 26
      asuSduInfoMultiControlBus      ASHealthState,      -- 27
      asuSduInfoCPUStatus            ASHealthState,      -- 28
      asuSduInfoTxMuteActual         TruthValue,         -- 29
      asuSduInfoRetLossToAntenna     Integer32,          -- 30
      asuSduInfoOutputFwdPower       Integer32,          -- 31
      asuSduInfoOutputRetPower       Integer32,          -- 32
      asuSduInfoAntennaBus           ASHealthState,      -- 33
      asuSduInfoRestartReason        ASRestartReason,    -- 34
      asuSduInfoUTCDateTime          ASDateTime,         -- 35
      asuSduInfoSWInstallDate        ASDateTime,         -- 36
      asuSduInfoInspectionDate       ASDateTime,         -- 37
      asuSduInfoOnGroundState        TruthValue          -- 38
   }

asuSduInfoIndex                           -- 1.3.6.1.4.1.13712.781.4.2.1.2.1.1
   OBJECT-TYPE
   SYNTAX Integer32 (1 .. 10)
   MAX-ACCESS read-only
   STATUS current
   DESCRIPTION "
      This object describes the unique identifier for the current unit."
   ::= { asuSduInfoEntry 1 }

asuSduInfoVendor                          -- 1.3.6.1.4.1.13712.781.4.2.1.2.1.2
   OBJECT-TYPE
   SYNTAX DisplayString (SIZE(0 .. 22))
   MAX-ACCESS read-only
   STATUS current
   DESCRIPTION "
      ASCII String with up to 22 characters to show the short name of the LRU vendor."
   ::= { asuSduInfoEntry 2 }

asuSduInfoHWPN                            -- 1.3.6.1.4.1.13712.781.4.2.1.2.1.3
   OBJECT-TYPE
   SYNTAX DisplayString (SIZE(0 .. 22))
   MAX-ACCESS read-only
   STATUS current
   DESCRIPTION "
      ASCII String with up to 22 characters to show the Hardware Part number of the
      LRU."
   ::= { asuSduInfoEntry 3 }

asuSduInfoSN                              -- 1.3.6.1.4.1.13712.781.4.2.1.2.1.4
   OBJECT-TYPE
   SYNTAX DisplayString (SIZE(0 .. 22))
   MAX-ACCESS read-only
   STATUS current
   DESCRIPTION "
      ASCII String with up to 22 characters to show the Hardware Serial Number of the
      LRU."
   ::= { asuSduInfoEntry 4 }

asuSduInfoHWFunction                      -- 1.3.6.1.4.1.13712.781.4.2.1.2.1.5
   OBJECT-TYPE
   SYNTAX DisplayString (SIZE(0 .. 22))
   MAX-ACCESS read-only
   STATUS current
   DESCRIPTION "
      ASCII String with up to 22 characters to show the Functional description of the
      LRU itself."
   ::= { asuSduInfoEntry 5 }

asuSduInfoDesignation                     -- 1.3.6.1.4.1.13712.781.4.2.1.2.1.6
   OBJECT-TYPE
   SYNTAX DisplayString (SIZE(0 .. 22))
   MAX-ACCESS read-only
   STATUS current
   DESCRIPTION "
      ASCII String with up to 22 characters to show the Short Name of the LRU."
   ::= { asuSduInfoEntry 6 }

asuSduInfoSWVersion                       -- 1.3.6.1.4.1.13712.781.4.2.1.2.1.7
   OBJECT-TYPE
   SYNTAX DisplayString (SIZE(0 .. 22))
   MAX-ACCESS read-only
   STATUS current
   DESCRIPTION "
      ASCII String with up to 22 characters to show the Software Version of the LRU."
   ::= { asuSduInfoEntry 7 }

asuSduInfoOverallStatus                   -- 1.3.6.1.4.1.13712.781.4.2.1.2.1.8
   OBJECT-TYPE
   SYNTAX ASHealthState
   MAX-ACCESS read-only
   STATUS current
   DESCRIPTION "
      General Status of the LRU."
   ::= { asuSduInfoEntry 8 }

asuSduInfoPowerOnSelfTest                 -- 1.3.6.1.4.1.13712.781.4.2.1.2.1.9
   OBJECT-TYPE
   SYNTAX ASTestState
   MAX-ACCESS read-only
   STATUS current
   DESCRIPTION "
      Shows the Power On Self-Test Results of the SDU."
   ::= { asuSduInfoEntry 9 }

asuSduInfoInteractiveSelfTest             -- 1.3.6.1.4.1.13712.781.4.2.1.2.1.10
   OBJECT-TYPE
   SYNTAX ASTestState
   MAX-ACCESS read-only
   STATUS current
   DESCRIPTION "
      Shows interactive self-test results of the SDU."
   ::= { asuSduInfoEntry 10 }

asuSduInfoFailureCode                     -- 1.3.6.1.4.1.13712.781.4.2.1.2.1.11
   OBJECT-TYPE
   SYNTAX Integer32
   MAX-ACCESS read-only
   STATUS current
   DESCRIPTION "
      This object defines a unique failure code for a test.
      The values are grouped
      - 0 to 999: This range is reserved for general standard codes
                  which have to be defined later.
      - > 1000:   This range is vendor specific fault code of latest
                  system error."
   ::= { asuSduInfoEntry 11 }

asuSduInfoFailureReason                   -- 1.3.6.1.4.1.13712.781.4.2.1.2.1.12
   OBJECT-TYPE
   SYNTAX DisplayString (SIZE(0 .. 255))
   MAX-ACCESS read-only
   STATUS current
   DESCRIPTION "
      Human readable vendor specific failure message related to the latest system
      error."
   ::= { asuSduInfoEntry 12 }

asuSduInfoTemperature                     -- 1.3.6.1.4.1.13712.781.4.2.1.2.1.13
   OBJECT-TYPE
   SYNTAX Integer32 (-65 .. 150)
   UNITS "degree Celsius"
   MAX-ACCESS read-only
   STATUS current
   DESCRIPTION "
      The temperature of the SDU in Celsius."
   ::= { asuSduInfoEntry 13 }

asuSduInfoThermState                      -- 1.3.6.1.4.1.13712.781.4.2.1.2.1.14
   OBJECT-TYPE
   SYNTAX ASUnitThermState
   MAX-ACCESS read-only
   STATUS current
   DESCRIPTION "
      Shows the thermal state of the SDU"
   ::= { asuSduInfoEntry 14 }

asuSduInfoCC1Status                       -- 1.3.6.1.4.1.13712.781.4.2.1.2.1.15
   OBJECT-TYPE
   SYNTAX ASHealthState
   MAX-ACCESS read-only
   STATUS current
   DESCRIPTION "
      Status of the channel card 1."
   ::= { asuSduInfoEntry 15 }

asuSduInfoCC2Status                       -- 1.3.6.1.4.1.13712.781.4.2.1.2.1.16
   OBJECT-TYPE
   SYNTAX ASHealthState
   MAX-ACCESS read-only
   STATUS current
   DESCRIPTION "
      Status of the channel card 2."
   ::= { asuSduInfoEntry 16 }

asuSduInfoIntHPAState                     -- 1.3.6.1.4.1.13712.781.4.2.1.2.1.17
   OBJECT-TYPE
   SYNTAX ASHealthState
   MAX-ACCESS read-only
   STATUS current
   DESCRIPTION "
      Status of the internal high power amplifier."
   ::= { asuSduInfoEntry 17 }

asuSduInfoQuadrax1Status                  -- 1.3.6.1.4.1.13712.781.4.2.1.2.1.18
   OBJECT-TYPE
   SYNTAX ASLinkState
   MAX-ACCESS read-only
   STATUS current
   DESCRIPTION "
      Status of the Ethernet quadrax port 1."
   ::= { asuSduInfoEntry 18 }

asuSduInfoQuadrax2Status                  -- 1.3.6.1.4.1.13712.781.4.2.1.2.1.19
   OBJECT-TYPE
   SYNTAX ASLinkState
   MAX-ACCESS read-only
   STATUS current
   DESCRIPTION "
      Status of the Ethernet quadrax port 2."
   ::= { asuSduInfoEntry 19 }

asuSduInfoIRS1BusStatus                   -- 1.3.6.1.4.1.13712.781.4.2.1.2.1.20
   OBJECT-TYPE
   SYNTAX ASHealthState
   MAX-ACCESS read-only
   STATUS current
   DESCRIPTION "
      Status of the IRS1 Bus."
   ::= { asuSduInfoEntry 20 }

asuSduInfoIRS1SystemStatus                -- 1.3.6.1.4.1.13712.781.4.2.1.2.1.21
   OBJECT-TYPE
   SYNTAX ASHealthState
   MAX-ACCESS read-only
   STATUS current
   DESCRIPTION "
      Status of the IRS1 Equipment."
   ::= { asuSduInfoEntry 21 }

asuSduInfoPSMState                        -- 1.3.6.1.4.1.13712.781.4.2.1.2.1.22
   OBJECT-TYPE
   SYNTAX ASHealthState
   MAX-ACCESS read-only
   STATUS current
   DESCRIPTION "
      Status of the Power Supply Module."
   ::= { asuSduInfoEntry 22 }

asuSduInfoOcxoState                       -- 1.3.6.1.4.1.13712.781.4.2.1.2.1.23
   OBJECT-TYPE
   SYNTAX ASHealthState
   MAX-ACCESS read-only
   STATUS current
   DESCRIPTION "
      Status of the Oven Controlled Crystal Oscillator."
   ::= { asuSduInfoEntry 23 }

asuSduInfoSecureORTStatus                 -- 1.3.6.1.4.1.13712.781.4.2.1.2.1.24
   OBJECT-TYPE
   SYNTAX ASHealthState
   MAX-ACCESS read-only
   STATUS current
   DESCRIPTION "
      Status of the secured Owner Requirements Table."
   ::= { asuSduInfoEntry 24 }

asuSduInfoUserORTStatus                   -- 1.3.6.1.4.1.13712.781.4.2.1.2.1.25
   OBJECT-TYPE
   SYNTAX ASHealthState
   MAX-ACCESS read-only
   STATUS current
   DESCRIPTION "
      Status of the user based Owner Requirements Table."
   ::= { asuSduInfoEntry 25 }

asuSduInfoStrapsState                     -- 1.3.6.1.4.1.13712.781.4.2.1.2.1.26
   OBJECT-TYPE
   SYNTAX TruthValue
   MAX-ACCESS read-only
   STATUS current
   DESCRIPTION "
      This value indicates, if the parity of configuration straps is valid or not.
       A true means it is valid and a false means that its not valid."
   ::= { asuSduInfoEntry 26 }

asuSduInfoMultiControlBus                 -- 1.3.6.1.4.1.13712.781.4.2.1.2.1.27
   OBJECT-TYPE
   SYNTAX ASHealthState
   MAX-ACCESS read-only
   STATUS current
   DESCRIPTION "
      This object indicates availability of ARINC 429 bus from CSDU to Antenna."
   ::= { asuSduInfoEntry 27 }

asuSduInfoCPUStatus                       -- 1.3.6.1.4.1.13712.781.4.2.1.2.1.28
   OBJECT-TYPE
   SYNTAX ASHealthState
   MAX-ACCESS read-only
   STATUS current
   DESCRIPTION "
      Status of the main Central Processing Unit."
   ::= { asuSduInfoEntry 28 }

asuSduInfoTxMuteActual                    -- 1.3.6.1.4.1.13712.781.4.2.1.2.1.29
   OBJECT-TYPE
   SYNTAX TruthValue
   MAX-ACCESS read-only
   STATUS current
   DESCRIPTION "
      Actual value of the TX mute discrete. True means muted and false means not
      muted."
   ::= { asuSduInfoEntry 29 }

asuSduInfoRetLossToAntenna                -- 1.3.6.1.4.1.13712.781.4.2.1.2.1.30
   OBJECT-TYPE
   SYNTAX Integer32
   UNITS "dbW"
   MAX-ACCESS read-only
   STATUS current
   DESCRIPTION "
      VSWR towards the Antenna in dbW."
   ::= { asuSduInfoEntry 30 }

asuSduInfoOutputFwdPower                  -- 1.3.6.1.4.1.13712.781.4.2.1.2.1.31
   OBJECT-TYPE
   SYNTAX Integer32
   UNITS "dbW"
   MAX-ACCESS read-only
   STATUS current
   DESCRIPTION "
      The output forward power in dbW."
   ::= { asuSduInfoEntry 31 }

asuSduInfoOutputRetPower                  -- 1.3.6.1.4.1.13712.781.4.2.1.2.1.32
   OBJECT-TYPE
   SYNTAX Integer32
   UNITS "dbW"
   MAX-ACCESS read-only
   STATUS current
   DESCRIPTION "
      The output return power in dbW."
   ::= { asuSduInfoEntry 32 }

asuSduInfoAntennaBus                      -- 1.3.6.1.4.1.13712.781.4.2.1.2.1.33
   OBJECT-TYPE
   SYNTAX ASHealthState
   MAX-ACCESS read-only
   STATUS current
   DESCRIPTION "
      State of the antenna bus."
   ::= { asuSduInfoEntry 33 }

asuSduInfoRestartReason                   -- 1.3.6.1.4.1.13712.781.4.2.1.2.1.34
   OBJECT-TYPE
   SYNTAX ASRestartReason
   MAX-ACCESS read-only
   STATUS current
   DESCRIPTION "
      The reason for the SDU's last restart."
   ::= { asuSduInfoEntry 34 }

asuSduInfoUTCDateTime                     -- 1.3.6.1.4.1.13712.781.4.2.1.2.1.35
   OBJECT-TYPE
   SYNTAX ASDateTime
   MAX-ACCESS read-only
   STATUS current
   DESCRIPTION "
      Current UTC date and time in RFC3339 format."
   ::= { asuSduInfoEntry 35 }

asuSduInfoSWInstallDate                   -- 1.3.6.1.4.1.13712.781.4.2.1.2.1.36
   OBJECT-TYPE
   SYNTAX ASDateTime
   MAX-ACCESS read-only
   STATUS current
   DESCRIPTION "
      The install date of the software in RFC3339 format. An empty string indicates
      that this value is not available."
   ::= { asuSduInfoEntry 36 }

asuSduInfoInspectionDate                  -- 1.3.6.1.4.1.13712.781.4.2.1.2.1.37
   OBJECT-TYPE
   SYNTAX ASDateTime
   MAX-ACCESS read-only
   STATUS current
   DESCRIPTION "
      The inspection date of the SDU in RFC3339 format. An empty string indicates
      that this value is not available."
   ::= { asuSduInfoEntry 37 }

asuSduInfoOnGroundState                   -- 1.3.6.1.4.1.13712.781.4.2.1.2.1.38
   OBJECT-TYPE
   SYNTAX TruthValue
   MAX-ACCESS read-only
   STATUS current
   DESCRIPTION "
      This value provides the SDU's version of the Air/Ground State. 
      True means on ground."
   ::= { asuSduInfoEntry 38 }
---------------------------------------------------------------------------------------
-- End of 'asuSduInfoTableTable'                                                     --
---------------------------------------------------------------------------------------

---------------------------------------------------------------------------------------
-- asUnits branch definition                                                         --
--    asuSDU sub branch definition                                                   --
--       asuSDUConfig sub sub branch definition                                      --
---------------------------------------------------------------------------------------
asuSDUConfig                              -- 1.3.6.1.4.1.13712.781.4.2.2
   OBJECT IDENTIFIER
   ::= { asuSDU 2 }

asuSduConfigTableNumbers                  -- 1.3.6.1.4.1.13712.781.4.2.2.1
   OBJECT-TYPE
   SYNTAX Integer32 (1 .. 100)
   MAX-ACCESS read-only
   STATUS current
   DESCRIPTION "
      This object indicates the number of entries in the SDU configuration table."
   ::= { asuSDUConfig 1 }

---------------------------------------------------------------------------------------
-- Objects related to the table for sdu configuration 'asuSduConfigTableTable'       --
---------------------------------------------------------------------------------------
asuSduConfigTable                         -- 1.3.6.1.4.1.13712.781.4.2.2.2
   OBJECT-TYPE
   SYNTAX SEQUENCE OF ASUSduConfigEntry
   MAX-ACCESS not-accessible
   STATUS current
   DESCRIPTION "
      Table provides details about configurabel parameters of the SDU."
   ::= { asuSDUConfig 2 }

asuSduConfigEntry                         -- 1.3.6.1.4.1.13712.781.4.2.2.2.1
   OBJECT-TYPE
   SYNTAX ASUSduConfigEntry
   MAX-ACCESS not-accessible
   STATUS current
   DESCRIPTION "
      Table entry holding parameters per LRU."
   INDEX { asuSduConfIndex }
   ::= { asuSduConfigTable 1 }

ASUSduConfigEntry
::= SEQUENCE {
      asuSduConfIndex                Integer32,         -- 01
      asuSduConfUTCDateTime          ASDateTime,        -- 02
      asuSduConfTxMuteRequested      TruthValue,        -- 03
      asuSduConfTailNumber           DisplayString,     -- 04
      asuSduConfCityPair             DisplayString,     -- 05
      asuSduConfFlightNumber         DisplayString,     -- 06
      asuSduConfFlightPhase          DisplayString,     -- 07
      asuSduConfClientOnGroundSate   TruthValue         -- 08
   }

asuSduConfIndex                           -- 1.3.6.1.4.1.13712.781.4.2.2.2.1.1
   OBJECT-TYPE
   SYNTAX Integer32 (1 .. 10)
   MAX-ACCESS read-only
   STATUS current
   DESCRIPTION "
      Unique identifier of the table entry."
   ::= { asuSduConfigEntry 1 }

asuSduConfUTCDateTime                     -- 1.3.6.1.4.1.13712.781.4.2.2.2.1.2
   OBJECT-TYPE
   SYNTAX ASDateTime
   MAX-ACCESS read-write
   STATUS current
   DESCRIPTION "
      This value allows a client to set the time in the SDU according to RFC3339."
   ::= { asuSduConfigEntry 2 }

asuSduConfTxMuteRequested                 -- 1.3.6.1.4.1.13712.781.4.2.2.2.1.3
   OBJECT-TYPE
   SYNTAX TruthValue
   MAX-ACCESS read-write
   STATUS current
   DESCRIPTION "
      Allows external equipment to request a state change of the TX mute discrete."
   ::= { asuSduConfigEntry 3 }

asuSduConfTailNumber                      -- 1.3.6.1.4.1.13712.781.4.2.2.2.1.4
   OBJECT-TYPE
   SYNTAX DisplayString (SIZE(0 .. 30))
   MAX-ACCESS read-write
   STATUS current
   DESCRIPTION "
      This field allows a client to provide the tail number of the current plane to
      the SDU."
   ::= { asuSduConfigEntry 4 }

asuSduConfCityPair                        -- 1.3.6.1.4.1.13712.781.4.2.2.2.1.5
   OBJECT-TYPE
   SYNTAX DisplayString (SIZE(0 .. 30))
   MAX-ACCESS read-write
   STATUS current
   DESCRIPTION "
      This field allows a client to provide the city-pair of the current flight to
      the SDU."
   ::= { asuSduConfigEntry 5 }

asuSduConfFlightNumber                    -- 1.3.6.1.4.1.13712.781.4.2.2.2.1.6
   OBJECT-TYPE
   SYNTAX DisplayString (SIZE(0 .. 30))
   MAX-ACCESS read-write
   STATUS current
   DESCRIPTION "
      This field allows a client to provide the Flight Number of the current flight
      to the SDU."
   ::= { asuSduConfigEntry 6 }

asuSduConfFlightPhase                     -- 1.3.6.1.4.1.13712.781.4.2.2.2.1.7
   OBJECT-TYPE
   SYNTAX DisplayString (SIZE(0 .. 30))
   MAX-ACCESS read-write
   STATUS current
   DESCRIPTION "
      This field allows a client to provide the actual flight phase to the SDU."
   ::= { asuSduConfigEntry 7 }

asuSduConfClientOnGroundSate              -- 1.3.6.1.4.1.13712.781.4.2.2.2.1.8
   OBJECT-TYPE
   SYNTAX TruthValue
   MAX-ACCESS read-write
   STATUS current
   DESCRIPTION "
      This field allows a client Application to provide its on ground state to the
      SDU. True means on ground. If the SDU has no other possibility to set its own
      on ground state it can copy this value into the info table value."
   ::= { asuSduConfigEntry 8 }
---------------------------------------------------------------------------------------
-- End of 'asssTestcaseTable'                                                        --
---------------------------------------------------------------------------------------

---------------------------------------------------------------------------------------
-- asUnits branch definition                                                         --
--    asuSDU sub branch definition                                                   --
--       asuSDUTraps sub sub branch definition                                       --
---------------------------------------------------------------------------------------
asuSDUTraps                               -- 1.3.6.1.4.1.13712.781.4.2.3
   OBJECT IDENTIFIER
   ::= { asuSDU 3 }

-- For this section are currently no identified sub objects

---------------------------------------------------------------------------------------
-- asUnits branch definition                                                         --
--    asuSCM sub branch definition                                                   --
---------------------------------------------------------------------------------------
asuSCMAvailable                           -- 1.3.6.1.4.1.13712.781.4.3
   OBJECT-TYPE
   SYNTAX TruthValue
   MAX-ACCESS read-only
   STATUS current
   DESCRIPTION "
      This object is has to set to true, if the system is supporting detailed SCM
      relevant information. Otherwise SDU relavant detail information will not be 
      supported."
   ::= { asUnits 3 }

asuSCM                                    -- 1.3.6.1.4.1.13712.781.4.4
   OBJECT IDENTIFIER
   ::= { asUnits 4 }

---------------------------------------------------------------------------------------
-- asUnits branch definition                                                         --
--    asuSCM sub branch definition                                                   --
--       asuSCMInfo sub sub branch definition                                        --
---------------------------------------------------------------------------------------
asuScmInfo                                -- 1.3.6.1.4.1.13712.781.4.4.1
   OBJECT IDENTIFIER
   ::= { asuSCM 1 }

asuScmInfoTableNumbers                    -- 1.3.6.1.4.1.13712.781.4.4.1.1
   OBJECT-TYPE
   SYNTAX Integer32 (1 .. 10)
   MAX-ACCESS read-only
   STATUS current
   DESCRIPTION "
      This object indicates the number of entries in the SCM info table."
   ::= { asuScmInfo 1 }

---------------------------------------------------------------------------------------
-- Objects related to the table for sdu informations 'asuScmInfoTable'               --
---------------------------------------------------------------------------------------
asuScmInfoTable                           -- 1.3.6.1.4.1.13712.781.4.4.1.2
   OBJECT-TYPE
   SYNTAX SEQUENCE OF ASUScmInfoEntry
   MAX-ACCESS not-accessible
   STATUS current
   DESCRIPTION "
      Table provides detailed information of each SCM, if suppoted."
   ::= { asuScmInfo 2 }

asuScmInfoEntry                           -- 1.3.6.1.4.1.13712.781.4.4.1.2.1
   OBJECT-TYPE
   SYNTAX ASUScmInfoEntry
   MAX-ACCESS not-accessible
   STATUS current
   DESCRIPTION "
      Table entry holding the parameters per SCM."
   INDEX { asuScmInfoIndex }
   ::= { asuScmInfoTable 1 }

ASUScmInfoEntry
::= SEQUENCE {
      asuScmInfoIndex                Integer32,         -- 01
      asuScmInfoVendor               DisplayString,     -- 02
      asuScmInfoHWPN                 DisplayString,     -- 03
      asuScmInfoSN                   DisplayString,     -- 04
      asuScmInfoHWFunction           DisplayString,     -- 05
      asuScmInfoDesignation          DisplayString,     -- 06
      asuScmInfoSWVersion            DisplayString,     -- 07
      asuScmInfoOverallStatus        ASHealthState,     -- 08
      asuScmInfoSimsInstalled        Integer32,         -- 09
      asuScmInfoIMSI1                DisplayString,     -- 10
      asuScmInfoIMSI2                DisplayString,     -- 11
      asuScmInfoIMSI3                DisplayString,     -- 12
      asuScmInfoIMSI4                DisplayString      -- 13
   }

asuScmInfoIndex                           -- 1.3.6.1.4.1.13712.781.4.4.1.2.1.1
   OBJECT-TYPE
   SYNTAX Integer32 (1 .. 10)
   MAX-ACCESS read-only
   STATUS current
   DESCRIPTION "
      This object describes the unique identifier for the current unit."
   ::= { asuScmInfoEntry 1 }

asuScmInfoVendor                          -- 1.3.6.1.4.1.13712.781.4.4.1.2.1.2
   OBJECT-TYPE
   SYNTAX DisplayString (SIZE(0 .. 22))
   MAX-ACCESS read-only
   STATUS current
   DESCRIPTION "
      ASCII String with up to 22 characters to show the short name of the LRU vendor."
   ::= { asuScmInfoEntry 2 }

asuScmInfoHWPN                            -- 1.3.6.1.4.1.13712.781.4.4.1.2.1.3
   OBJECT-TYPE
   SYNTAX DisplayString (SIZE(0 .. 22))
   MAX-ACCESS read-only
   STATUS current
   DESCRIPTION "
      ASCII String with up to 22 characters to show the Hardware Part number of the
      LRU."
   ::= { asuScmInfoEntry 3 }

asuScmInfoSN                              -- 1.3.6.1.4.1.13712.781.4.4.1.2.1.4
   OBJECT-TYPE
   SYNTAX DisplayString (SIZE(0 .. 22))
   MAX-ACCESS read-only
   STATUS current
   DESCRIPTION "
      ASCII String with up to 22 characters to show the Hardware Serial Number of the
      LRU."
   ::= { asuScmInfoEntry 4 }

asuScmInfoHWFunction                      -- 1.3.6.1.4.1.13712.781.4.4.1.2.1.5
   OBJECT-TYPE
   SYNTAX DisplayString (SIZE(0 .. 22))
   MAX-ACCESS read-only
   STATUS current
   DESCRIPTION "
      ASCII String with up to 22 characters to show the Functional description of the
      unit itself."
   ::= { asuScmInfoEntry 5 }

asuScmInfoDesignation                     -- 1.3.6.1.4.1.13712.781.4.4.1.2.1.6
   OBJECT-TYPE
   SYNTAX DisplayString (SIZE(0 .. 22))
   MAX-ACCESS read-only
   STATUS current
   DESCRIPTION "
      ASCII String with up to 22 characters to show the Short Name of the LRU."
   ::= { asuScmInfoEntry 6 }

asuScmInfoSWVersion                       -- 1.3.6.1.4.1.13712.781.4.4.1.2.1.7
   OBJECT-TYPE
   SYNTAX DisplayString (SIZE(0 .. 22))
   MAX-ACCESS read-only
   STATUS current
   DESCRIPTION "
      ASCII String with up to 22 characters to show the Software Version of the
      LRU."
   ::= { asuScmInfoEntry 7 }

asuScmInfoOverallStatus                   -- 1.3.6.1.4.1.13712.781.4.4.1.2.1.8
   OBJECT-TYPE
   SYNTAX ASHealthState
   MAX-ACCESS read-only
   STATUS current
   DESCRIPTION "
      General Status of the unit."
   ::= { asuScmInfoEntry 8 }

asuScmInfoSimsInstalled                   -- 1.3.6.1.4.1.13712.781.4.4.1.2.1.9
   OBJECT-TYPE
   SYNTAX Integer32 (0 .. 4)
   MAX-ACCESS read-only
   STATUS current
   DESCRIPTION "
      The number of SIMS installed in the SCM. The following four objects are
      containing useful IMSI numbers depending on this object."
   ::= { asuScmInfoEntry 9 }

asuScmInfoIMSI1                           -- 1.3.6.1.4.1.13712.781.4.4.1.2.1.10
   OBJECT-TYPE
   SYNTAX DisplayString (SIZE(0 .. 30))
   MAX-ACCESS read-only
   STATUS current
   DESCRIPTION "
      ASCII String with up to 30 characters to show the IMSI number of SIM card 1
      (e.g. +17659850986). If less then 1 SIMS are installed this parameter has to
      contain an empty string."
   ::= { asuScmInfoEntry 10 }

asuScmInfoIMSI2                           -- 1.3.6.1.4.1.13712.781.4.4.1.2.1.11
   OBJECT-TYPE
   SYNTAX DisplayString (SIZE(0 .. 30))
   MAX-ACCESS read-only
   STATUS current
   DESCRIPTION "
      ASCII String with up to 30 characters to show the IMSI number of SIM card 2
      (e.g. +17659850987). If less then 2 SIMS are installed this parameter has to
      contain an empty string."
   ::= { asuScmInfoEntry 11 }

asuScmInfoIMSI3                           -- 1.3.6.1.4.1.13712.781.4.4.1.2.1.12
   OBJECT-TYPE
   SYNTAX DisplayString (SIZE(0 .. 30))
   MAX-ACCESS read-only
   STATUS current
   DESCRIPTION "
      ASCII String with up to 30 characters to show the IMSI number of SIM card 3
      (e.g. +17659850988). If less then 3 SIMS are installed this parameter has to
      contain an empty string."
   ::= { asuScmInfoEntry 12 }

asuScmInfoIMSI4                           -- 1.3.6.1.4.1.13712.781.4.4.1.2.1.13
   OBJECT-TYPE
   SYNTAX DisplayString (SIZE(0 .. 30))
   MAX-ACCESS read-only
   STATUS current
   DESCRIPTION "
      ASCII String with up to 30 characters to show the IMSI number of SIM card 4
      (e.g. +17659850989). If less then 4 SIMS are installed this parameter has to
      contain an empty string."
   ::= { asuScmInfoEntry 13 }
---------------------------------------------------------------------------------------
-- End of 'asuScmInfoTable'                                                          --
---------------------------------------------------------------------------------------

---------------------------------------------------------------------------------------
-- asUnits branch definition                                                         --
--    asuSCM sub branch definition                                                   --
--       asuSCMConfig sub sub branch definition                                      --
---------------------------------------------------------------------------------------
asuSCMConfig                              -- 1.3.6.1.4.1.13712.781.4.4.2
   OBJECT IDENTIFIER
   ::= { asuSCM 2 }

-- For this section are currently no identified sub objects

---------------------------------------------------------------------------------------
-- asUnits branch definition                                                         --
--    asuSCM sub branch definition                                                   --
--       asuSCMTraps sub sub branch definition                                       --
---------------------------------------------------------------------------------------
asuSCMTraps                               -- 1.3.6.1.4.1.13712.781.4.4.3
   OBJECT IDENTIFIER
   ::= { asuSCM 3 }

-- For this section are currently no identified sub objects

---------------------------------------------------------------------------------------
-- asUnits branch definition                                                         --
--    asuDLNA sub branch definition                                                  --
---------------------------------------------------------------------------------------
asuDLNAAvailable                          -- 1.3.6.1.4.1.13712.781.4.5
   OBJECT-TYPE
   SYNTAX TruthValue
   MAX-ACCESS read-only
   STATUS current
   DESCRIPTION "
      This object is has to set to true, if the system is supporting detailed DLNA
      relevant information. Otherwise SDU relavant detail information will not be
      supported."
   ::= { asUnits 5 }

asuDLNA                                   -- 1.3.6.1.4.1.13712.781.4.6
   OBJECT IDENTIFIER
   ::= { asUnits 6 }

---------------------------------------------------------------------------------------
-- asUnits branch definition                                                         --
--    asuDLNA sub branch definition                                                  --
--       asuDLNAInfo sub sub branch definition                                       --
---------------------------------------------------------------------------------------
asuDlnaInfo                               -- 1.3.6.1.4.1.13712.781.4.6.1
   OBJECT IDENTIFIER
   ::= { asuDLNA 1 }

asuDlnaInfoTableNumbers                   -- 1.3.6.1.4.1.13712.781.4.6.1.1
   OBJECT-TYPE
   SYNTAX Integer32 (1 .. 10)
   MAX-ACCESS read-only
   STATUS current
   DESCRIPTION "
      This object indicates the number of entries in the DLNA info table."
   ::= { asuDlnaInfo 1 }

---------------------------------------------------------------------------------------
-- Objects related to the table for sdu informations 'asuSduInfoTable'               --
---------------------------------------------------------------------------------------
asuDlnaInfoTable                          -- 1.3.6.1.4.1.13712.781.4.6.1.2
   OBJECT-TYPE
   SYNTAX SEQUENCE OF ASUDlnaInfoEntry
   MAX-ACCESS not-accessible
   STATUS current
   DESCRIPTION "
      Table providing detailed information per equipped DLNA, if supported."
   ::= { asuDlnaInfo 2 }

asuDlnaInfoEntry                          -- 1.3.6.1.4.1.13712.781.4.6.1.2.1
   OBJECT-TYPE
   SYNTAX ASUDlnaInfoEntry
   MAX-ACCESS not-accessible
   STATUS current
   DESCRIPTION "
      Table entry holding parameters per equipped DLNA."
   INDEX { asuDlnaInfoIndex }
   ::= { asuDlnaInfoTable 1 }

ASUDlnaInfoEntry
::= SEQUENCE {
      asuDlnaInfoIndex                Integer32,         -- 01
      asuDlnaInfoVendor               DisplayString,     -- 02
      asuDlnaInfoHWPN                 DisplayString,     -- 03
      asuDlnaInfoSN                   DisplayString,     -- 04
      asuDlnaInfoHWFunction           DisplayString,     -- 05
      asuDlnaInfoDesignation          DisplayString,     -- 06
      asuDlnaInfoSWVersion            DisplayString,     -- 07
      asuDlnaInfoOverallStatus        ASHealthState      -- 08
   }

asuDlnaInfoIndex                          -- 1.3.6.1.4.1.13712.781.4.6.1.2.1.1
   OBJECT-TYPE
   SYNTAX Integer32 (1 .. 10)
   MAX-ACCESS read-only
   STATUS current
   DESCRIPTION "
      This object describes the unique identifier for the current unit."
   ::= { asuDlnaInfoEntry 1 }

asuDlnaInfoVendor                         -- 1.3.6.1.4.1.13712.781.4.6.1.2.1.2
   OBJECT-TYPE
   SYNTAX DisplayString (SIZE(0 .. 22))
   MAX-ACCESS read-only
   STATUS current
   DESCRIPTION "
      ASCII String with up to 22 characters to show the Short name of the LRU vendor."
   ::= { asuDlnaInfoEntry 2 }

asuDlnaInfoHWPN                           -- 1.3.6.1.4.1.13712.781.4.6.1.2.1.3
   OBJECT-TYPE
   SYNTAX DisplayString (SIZE(0 .. 22))
   MAX-ACCESS read-only
   STATUS current
   DESCRIPTION "
      ASCII String with up to 22 characters to show the Hardware Part number of the
      LRU."
   ::= { asuDlnaInfoEntry 3 }

asuDlnaInfoSN                             -- 1.3.6.1.4.1.13712.781.4.6.1.2.1.4
   OBJECT-TYPE
   SYNTAX DisplayString (SIZE(0 .. 22))
   MAX-ACCESS read-only
   STATUS current
   DESCRIPTION "
      ASCII String with up to 22 characters to show the Hardware Serial Number of the
      LRU."
   ::= { asuDlnaInfoEntry 4 }

asuDlnaInfoHWFunction                     -- 1.3.6.1.4.1.13712.781.4.6.1.2.1.5
   OBJECT-TYPE
   SYNTAX DisplayString (SIZE(0 .. 22))
   MAX-ACCESS read-only
   STATUS current
   DESCRIPTION "
      ASCII String with up to 22 characters to show the Functional description of the
      LRU itself."
   ::= { asuDlnaInfoEntry 5 }

asuDlnaInfoDesignation                    -- 1.3.6.1.4.1.13712.781.4.6.1.2.1.6
   OBJECT-TYPE
   SYNTAX DisplayString (SIZE(0 .. 22))
   MAX-ACCESS read-only
   STATUS current
   DESCRIPTION "
      ASCII String with up to 22 characters to show the Short Name of the LRU."
   ::= { asuDlnaInfoEntry 6 }

asuDlnaInfoSWVersion                      -- 1.3.6.1.4.1.13712.781.4.6.1.2.1.7
   OBJECT-TYPE
   SYNTAX DisplayString (SIZE(0 .. 22))
   MAX-ACCESS read-only
   STATUS current
   DESCRIPTION "
      ASCII String with up to 22 characters to show the Software Version of the LRU."
   ::= { asuDlnaInfoEntry 7 }

asuDlnaInfoOverallStatus                  -- 1.3.6.1.4.1.13712.781.4.6.1.2.1.8
   OBJECT-TYPE
   SYNTAX ASHealthState
   MAX-ACCESS read-only
   STATUS current
   DESCRIPTION "
      General Status of the LRU."
   ::= { asuDlnaInfoEntry 8 }

---------------------------------------------------------------------------------------
-- End of 'asuScmInfoTable'                                                          --
---------------------------------------------------------------------------------------

---------------------------------------------------------------------------------------
-- asUnits branch definition                                                         --
--    asuDLNA sub branch definition                                                  --
--       asuDLNAConfig sub sub branch definition                                     --
---------------------------------------------------------------------------------------
asuDlnaConfig                             -- 1.3.6.1.4.1.13712.781.4.6.2
   OBJECT IDENTIFIER
   ::= { asuDLNA 2 }

-- For this section are currently no identified sub objects

---------------------------------------------------------------------------------------
-- asUnits branch definition                                                         --
--    asuDLNA sub branch definition                                                  --
--       asuDLNATraps sub sub branch definition                                      --
---------------------------------------------------------------------------------------
asuDlnaTraps                              -- 1.3.6.1.4.1.13712.781.4.6.2
   OBJECT IDENTIFIER
   ::= { asuDLNA 3 }

-- For this section are currently no identified sub objects

---------------------------------------------------------------------------------------
-- asUnits branch definition                                                         --
--    asuAntenna sub branch definition                                               --
---------------------------------------------------------------------------------------
asuAntennaAvailable                       -- 1.3.6.1.4.1.13712.781.4.7
   OBJECT-TYPE
   SYNTAX TruthValue
   MAX-ACCESS read-only
   STATUS current
   DESCRIPTION "
      This object is has to set to true, if the system is supporting detailed Antenna
      relevant information. Otherwise SDU relavant detail information will not be
      supported."
   ::= { asUnits 7 }

asuAntenna                                -- 1.3.6.1.4.1.13712.781.4.8
   OBJECT IDENTIFIER
   ::= { asUnits 8 }

---------------------------------------------------------------------------------------
-- asUnits branch definition                                                         --
--    asuAntenna sub branch definition                                               --
--       asuAntInfo sub sub branch definition                                        --
---------------------------------------------------------------------------------------
asuAntInfo                                -- 1.3.6.1.4.1.13712.781.4.8.1
   OBJECT IDENTIFIER
   ::= { asuAntenna 1 }

asuAntInfoTableNumbers                    -- 1.3.6.1.4.1.13712.781.4.8.1.1
   OBJECT-TYPE
   SYNTAX Integer32 (1 .. 10)
   MAX-ACCESS read-only
   STATUS current
   DESCRIPTION "
      This object indicates the number of entries in the Antenna info table."
   ::= { asuAntInfo 1 }

---------------------------------------------------------------------------------------
-- Objects related to the table for sdu informations 'asuAntInfoTable'               --
---------------------------------------------------------------------------------------
asuAntInfoTable                           -- 1.3.6.1.4.1.13712.781.4.8.1.2
   OBJECT-TYPE
   SYNTAX SEQUENCE OF ASUAntInfoEntry
   MAX-ACCESS not-accessible
   STATUS current
   DESCRIPTION "
      Table providing details of each connected Antenna."
   ::= { asuAntInfo 2 }

asuAntInfoEntry                           -- 1.3.6.1.4.1.13712.781.4.8.1.2.1
   OBJECT-TYPE
   SYNTAX ASUAntInfoEntry
   MAX-ACCESS not-accessible
   STATUS current
   DESCRIPTION "
      Table entry holding parameters per connected antenna."
   INDEX { asuAntInfoIndex }
   ::= { asuAntInfoTable 1 }

ASUAntInfoEntry
::= SEQUENCE {
      asuAntInfoIndex                Integer32,         -- 01
      asuAntInfoVendor               DisplayString,     -- 02
      asuAntInfoHWPN                 DisplayString,     -- 03
      asuAntInfoSN                   DisplayString,     -- 04
      asuAntInfoHWFunction           DisplayString,     -- 05
      asuAntInfoDesignation          DisplayString,     -- 06
      asuAntInfoSWVersion            DisplayString,     -- 07
      asuAntInfoOverallStatus        ASHealthState,    -- 08
      asuAntInfoTemperatureStatus    ASAntThermState,   -- 09
      asuAntInfoGain                 Integer32          -- 10
   }

asuAntInfoIndex                           -- 1.3.6.1.4.1.13712.781.4.8.1.2.1.1
   OBJECT-TYPE
   SYNTAX Integer32 (1 .. 10)
   MAX-ACCESS read-only
   STATUS current
   DESCRIPTION "
      This object describes the unique identifier for the current antenna."
   ::= { asuAntInfoEntry 1 }

asuAntInfoVendor                          -- 1.3.6.1.4.1.13712.781.4.8.1.2.1.2
   OBJECT-TYPE
   SYNTAX DisplayString (SIZE(0 .. 22))
   MAX-ACCESS read-only
   STATUS current
   DESCRIPTION "
      ASCII String with up to 22 characters to show the short name of the vendor from
      the referred antenna."
   ::= { asuAntInfoEntry 2 }

asuAntInfoHWPN                            -- 1.3.6.1.4.1.13712.781.4.8.1.2.1.3
   OBJECT-TYPE
   SYNTAX DisplayString (SIZE(0 .. 22))
   MAX-ACCESS read-only
   STATUS current
   DESCRIPTION "
      ASCII String with up to 22 characters to show the Hardware Part number of the
      antenna."
   ::= { asuAntInfoEntry 3 }

asuAntInfoSN                              -- 1.3.6.1.4.1.13712.781.4.8.1.2.1.4
   OBJECT-TYPE
   SYNTAX DisplayString (SIZE(0 .. 22))
   MAX-ACCESS read-only
   STATUS current
   DESCRIPTION "
      ASCII String with up to 22 characters to show the Hardware Serial Number of the
      antenna."
   ::= { asuAntInfoEntry 4 }

asuAntInfoHWFunction                      -- 1.3.6.1.4.1.13712.781.4.8.1.2.1.5
   OBJECT-TYPE
   SYNTAX DisplayString (SIZE(0 .. 22))
   MAX-ACCESS read-only
   STATUS current
   DESCRIPTION "
      ASCII String with up to 22 characters to show the Functional description of the
      antenna."
   ::= { asuAntInfoEntry 5 }

asuAntInfoDesignation                     -- 1.3.6.1.4.1.13712.781.4.8.1.2.1.6
   OBJECT-TYPE
   SYNTAX DisplayString (SIZE(0 .. 22))
   MAX-ACCESS read-only
   STATUS current
   DESCRIPTION "
      ASCII String with up to 22 characters to show the Short Name of the antenna."
   ::= { asuAntInfoEntry 6 }

asuAntInfoSWVersion                       -- 1.3.6.1.4.1.13712.781.4.8.1.2.1.7
   OBJECT-TYPE
   SYNTAX DisplayString (SIZE(0 .. 22))
   MAX-ACCESS read-only
   STATUS current
   DESCRIPTION "
      ASCII String with up to 22 characters to show the Software Version of the antenna."
   ::= { asuAntInfoEntry 7 }

asuAntInfoOverallStatus                   -- 1.3.6.1.4.1.13712.781.4.8.1.2.1.8
   OBJECT-TYPE
   SYNTAX ASHealthState
   MAX-ACCESS read-only
   STATUS current
   DESCRIPTION "
      General Status of the antenna."
   ::= { asuAntInfoEntry 8 }

asuAntInfoTemperatureStatus               -- 1.3.6.1.4.1.13712.781.4.8.1.2.1.9
   OBJECT-TYPE
   SYNTAX ASAntThermState
   MAX-ACCESS read-only
   STATUS current
   DESCRIPTION "
      Thermal state of the antenna."
   ::= { asuAntInfoEntry 9}

asuAntInfoGain                            -- 1.3.6.1.4.1.13712.781.4.8.1.2.1.10
   OBJECT-TYPE
   SYNTAX Integer32 (0 .. 315)
   UNITS "db/10"
   MAX-ACCESS read-only
   STATUS current
   DESCRIPTION "
      The antenna gain currently utilized from 0.0 to 31.5 dB."
   ::= { asuAntInfoEntry 10}
---------------------------------------------------------------------------------------
-- End of 'asuAntInfoTable'                                                          --
---------------------------------------------------------------------------------------

---------------------------------------------------------------------------------------
-- asUnits branch definition                                                         --
--    asuAntenna sub branch definition                                               --
--       asuAntConfig sub sub branch definition                                      --
---------------------------------------------------------------------------------------
asuAntConfig                              -- 1.3.6.1.4.1.13712.781.4.8.2
   OBJECT IDENTIFIER
   ::= { asuAntenna 2 }

-- For this section are currently no identified sub objects

---------------------------------------------------------------------------------------
-- asUnits branch definition                                                         --
--    asuAntenna sub branch definition                                               --
--       asuAntTraps sub sub branch definition                                       --
---------------------------------------------------------------------------------------
asuAntTraps                               -- 1.3.6.1.4.1.13712.781.4.8.3
   OBJECT IDENTIFIER
   ::= { asuAntenna 3 }

-- For this section are currently no identified sub objects

---------------------------------------------------------------------------------------
-- asUserDefArea branch definition                                                   --
---------------------------------------------------------------------------------------
asudaEMS                                  -- 1.3.6.1.4.1.13712.781.5.1
   OBJECT IDENTIFIER
   ::= { asUserDefArea 1 }

asudaEmsVersionMajor                      -- 1.3.6.1.4.1.13712.781.5.1.1
   OBJECT-TYPE
   SYNTAX Integer32
   MAX-ACCESS read-only
   STATUS current
   DESCRIPTION "
      This object defines the major version of the EMS specific sub branch. The current
      predefined default major version number is 0 to indicate an empty sub branch."
   DEFVAL { 0 }
   ::= { asudaEMS 1 }

asudaEmsVersionMinor                      -- 1.3.6.1.4.1.13712.781.5.1.2
   OBJECT-TYPE
   SYNTAX Integer32 (0 .. 99)
   MAX-ACCESS read-only
   STATUS current
   DESCRIPTION "
      This object defines the minor version of the EMS specific sub branch. The current
      predefined default minor version number is 0."
   DEFVAL { 0 }
   ::= { asudaEMS 2 }

asudaHoneywell                            -- 1.3.6.1.4.1.13712.781.5.2
   OBJECT IDENTIFIER
   ::= { asUserDefArea 2 }

asudaHoneywellVersionMajor                -- 1.3.6.1.4.1.13712.781.5.2.1
   OBJECT-TYPE
   SYNTAX Integer32
   MAX-ACCESS read-only
   STATUS current
   DESCRIPTION "
      This object defines the major version of the Honeywell specific sub branch. The
      current predefined default major version number is 0 to indicate an empty sub
      branch."
   DEFVAL { 0 }
   ::= { asudaHoneywell 1 }

asudaHoneywellVersionMinor                -- 1.3.6.1.4.1.13712.781.5.2.2
   OBJECT-TYPE
   SYNTAX Integer32 (0 .. 99)
   MAX-ACCESS read-only
   STATUS current
   DESCRIPTION "
      This object defines the minor version of the Honeywell specific sub branch. The
      current predefined default minor version number is 0."
   DEFVAL { 0 }
   ::= { asudaHoneywell 2 }

asudaRockColl                             -- 1.3.6.1.4.1.13712.781.5.3
   OBJECT IDENTIFIER
   ::= { asUserDefArea 3 }

asudaRockCollVersionMajor                 -- 1.3.6.1.4.1.13712.781.5.3.1
   OBJECT-TYPE
   SYNTAX Integer32
   MAX-ACCESS read-only
   STATUS current
   DESCRIPTION "
      This object defines the major version of the Rockwell Collins specific sub branch
      The current predefined default major version number is 0 to indicate an empty sub
      branch."
   DEFVAL { 0 }
   ::= { asudaRockColl 1 }

asudaRockCollVersionMinor                 -- 1.3.6.1.4.1.13712.781.5.3.2
   OBJECT-TYPE
   SYNTAX Integer32 (0 .. 99)
   MAX-ACCESS read-only
   STATUS current
   DESCRIPTION "
      This object defines the minor version of the Rockwell Collins specific sub 
      branch. The current predefined default minor version number is 0."
   DEFVAL { 0 }
   ::= { asudaRockColl 2 }

asudaThales                               -- 1.3.6.1.4.1.13712.781.5.4
   OBJECT IDENTIFIER
   ::= { asUserDefArea 4 }

asudaThalesVersionMajor                   -- 1.3.6.1.4.1.13712.781.5.4.1
   OBJECT-TYPE
   SYNTAX Integer32
   MAX-ACCESS read-only
   STATUS current
   DESCRIPTION "
      This object defines the major version of the Thales specific sub branch. The
      current predefined default major version number is 0 to indicate an empty sub
      branch."
   DEFVAL { 0 }
   ::= { asudaThales 1 }

asudaThalesVersionMinor                   -- 1.3.6.1.4.1.13712.781.5.4.2
   OBJECT-TYPE
   SYNTAX Integer32 (0 .. 99)
   MAX-ACCESS read-only
   STATUS current
   DESCRIPTION "
      This object defines the minor version of the Thales specific sub branch. The
      current predefined default minor version number is 0."
   DEFVAL { 0 }
   ::= { asudaThales 2 }

asudaThrane                               -- 1.3.6.1.4.1.13712.781.5.5
   OBJECT IDENTIFIER
   ::= { asUserDefArea 5 }

asudaThraneVersionMajor                   -- 1.3.6.1.4.1.13712.781.5.5.1
   OBJECT-TYPE
   SYNTAX Integer32
   MAX-ACCESS read-only
   STATUS current
   DESCRIPTION "
      This object defines the major version of the Thrane & Thrane specific sub branch.
      The current predefined default major version number is 0 to indicate an empty sub
      branch."
   DEFVAL { 0 }
   ::= { asudaThrane 1 }

asudaThraneVersionMinor                   -- 1.3.6.1.4.1.13712.781.5.5.2
   OBJECT-TYPE
   SYNTAX Integer32 (0 .. 99)
   MAX-ACCESS read-only
   STATUS current
   DESCRIPTION "
      This object defines the minor version of the Thrane & Thrane specific sub branch.
      The current predefined default minor version number is 0."
   DEFVAL { 0 }
   ::= { asudaThrane 2 }

asudaChelton                              -- 1.3.6.1.4.1.13712.781.5.6
   OBJECT IDENTIFIER
   ::= { asUserDefArea 6 }

asudaCheltonVersionMajor                  -- 1.3.6.1.4.1.13712.781.5.6.1
   OBJECT-TYPE
   SYNTAX Integer32
   MAX-ACCESS read-only
   STATUS current
   DESCRIPTION "
      This object defines the major version of the Chelton specific sub branch. The
      current predefined default major version number is 0 to indicate an empty sub
      branch."
   DEFVAL { 0 }
   ::= { asudaChelton 1 }

asudaCheltonVersionMinor                  -- 1.3.6.1.4.1.13712.781.5.6.2
   OBJECT-TYPE
   SYNTAX Integer32 (0 .. 99)
   MAX-ACCESS read-only
   STATUS current
   DESCRIPTION "
      This object defines the minor version of the Chelton specific sub branch. The
      current predefined default minor version number is 0."
   DEFVAL { 0 }
   ::= { asudaChelton 2 }

END
---------------------------------------------------------------------------------------
--                                                                                   --
--                          End of ArincSwift-MIB Definion                           --
--                                                                                   --
---------------------------------------------------------------------------------------
